;;||==============================||;;
;;||   AG Layers AIA v5           ||;;
;;||   www.LetsBIMtogether.com    ||;;
;;||==============================||;;
;;||
;;||   Commands: LayAIAcreateAll
;;||             LayAIAcreateOnly
;;||             LayAIAdeleteAll
;;||             LayAIAdeleteOnly
;;||
;;||   LayAIAcreateOnly / LayAIAdeleteOnly Codes:
;;||
;;||      MEP  = M (Mechanical) + E (Electrical) + P (Plumbing)
;;||      AMEP = A (Architecture) + M (Mechanical) + E (Electrical) + P (Plumbing)
;;||
;;||      A = Architecture         B = Geotechnical
;;||      C = Civil                E = Electrical
;;||      F = Fire Protection      G = General
;;||      H = Hazardous Materials  I = Interiors
;;||      L = Landscape            M = Mechanical
;;||      P = Plumbing             Q = Equipment
;;||      R = Resource             S = Structural
;;||      T = Telecommunications   V = Survey/Mapping
;;||      X = Other Disciplines

;; ============================================================
;; AIA/NCS CAD Layer Guidelines - US National CAD Standard v5
;;
;; NOTE: Independent implementation of AIA/NCS CAD Layer
;; Guidelines. Not affiliated with or endorsed by the AIA.
;;
;; SOURCES:
;; https://facilities.duke.edu/sites/default/files/AIA%20CAD%20Layer%20Guidelines.pdf
;; https://www.autodesk.com/support/technical/article/caas/sfdcarticles/sfdcarticles/How-to-set-up-AIA-Layer-Standards-in-AutoCAD-LT.html
;; ============================================================

(vl-load-com)

;;------------------------------------------------------------
;; PART 1: Low level helpers
;;------------------------------------------------------------

(defun load-ltype (lt)
  (if (and lt
           (not (equal lt "Continuous"))
           (not (tblsearch "LTYPE" lt)))
    (vl-cmdf "-LINETYPE" "LOAD" lt "acad.lin" "")
  )
)

(defun make-layer (name color ltype desc)
  (if (not (tblsearch "LAYER" name))
    (progn
      (load-ltype ltype)
      (entmake
        (list
          '(0 . "LAYER")
          '(100 . "AcDbSymbolTableRecord")
          '(100 . "AcDbLayerTableRecord")
          (cons 2  name)
          '(70 . 0)
          (cons 62 color)
          (cons 6  ltype)
          '(290 . 1)
          '(370 . -3)
        )
      )
      (if (and desc (not (equal desc "")))
        (vla-put-description
          (vla-item
            (vla-get-layers (vla-get-activedocument (vlax-get-acad-object)))
            name)
          desc)
      )
      (setq lay-count (1+ lay-count))
    )
  )
)

(defun delete-layer (name color ltype desc / lyr)
  ;; Signature mirrors make-layer so (apply 'delete-layer row) works on
  ;; the same data rows. color / ltype / desc are accepted but unused.
  (if (tblsearch "LAYER" name)
    (if (equal (strcase name) (strcase (getvar "CLAYER")))
      (setq del-skip (1+ del-skip))
      (progn
        (setq lyr
          (vla-item
            (vla-get-layers (vla-get-activedocument (vlax-get-acad-object)))
            name))
        (vl-catch-all-apply 'vla-delete (list lyr))
        (if (not (tblsearch "LAYER" name))
          (setq del-count (1+ del-count))
          (setq del-skip  (1+ del-skip))
        )
      )
    )
  )
)

;;------------------------------------------------------------
;; PART 2: UI helpers
;;------------------------------------------------------------

(defun aia-header (mode)
  (setq lay-count 0
        del-count 0
        del-skip  0)
  (setvar "CMDECHO" 0)
  (princ "\n====================================================")
  (princ "\n  AG Layers AIA v5  - AIA/NCS v5 Layer Generator")
  (princ "\n====================================================")
)

(defun aia-footer (mode)
  (setvar "CMDECHO" 1)
  (princ "\n")
  (princ "\n====================================================")
  (princ (strcat "\n  AG Layers AIA v5 - " mode " COMPLETE"))
  (princ "\n====================================================")
  (if (equal mode "CREATE")
    (progn
      (princ (strcat "\n  LAYERS CREATED : " (itoa lay-count)))
      (princ "\n  Run LAYER command to review all layers.")
      (princ "\n  Note: Existing layers were skipped.")
    )
  )
  (if (equal mode "DELETE")
    (progn
      (princ (strcat "\n  LAYERS DELETED : " (itoa del-count)))
      (princ (strcat "\n  LAYERS SKIPPED : " (itoa del-skip)
                     " (current layer or layer in use)"))
      (princ "\n  Run LAYER command to review remaining layers.")
    )
  )
  (princ "\n====================================================\n")
  (princ)
)

;;------------------------------------------------------------
;; PART 3: Layer data definitions
;;------------------------------------------------------------

(setq *layers-A*
  (list
    (list "A-ANNO-DIMS" 1 "Continuous" "Dimensions")
    (list "A-ANNO-TEXT" 2 "Continuous" "Text")
    (list "A-AREA" 2 "Continuous" "Area")
    (list "A-AREA-OCCP" 2 "Continuous" "Area: occupant or employee names")
    (list "A-BARR" 243 "Continuous" "Barrier")
    (list "A-BARR-AIR" 2 "Continuous" "Barrier: air")
    (list "A-CLNG" 30 "Continuous" "Ceiling")
    (list "A-CLNG-ACCS" 30 "Continuous" "Ceiling: access")
    (list "A-CLNG-GRID" 30 "Continuous" "Ceiling: grid")
    (list "A-CLNG-OPNG" 30 "Continuous" "Ceiling: openings")
    (list "A-CLNG-SUSP" 30 "Continuous" "Ceiling: suspended elements")
    (list "A-CLNG-TEES" 30 "Continuous" "Ceiling: main tees")
    (list "A-COLS" 7 "Continuous" "Columns")
    (list "A-CONV" 4 "Continuous" "Conveying systems")
    (list "A-DOOR" 3 "Continuous" "Doors")
    (list "A-DOOR-FULL" 3 "Continuous" "Doors: full-height (swing and leaf)")
    (list "A-DOOR-PRHT" 3 "Continuous" "Doors: partial-height (swing and leaf)")
    (list "A-EQPM" 4 "Continuous" "Equipment")
    (list "A-EQPM-ACCS" 4 "Continuous" "Equipment: access")
    (list "A-EQPM-FIXD" 4 "Continuous" "Equipment: fixed")
    (list "A-EQPM-OVHD" 4 "Continuous" "Equipment: overhead")
    (list "A-FLOR" 2 "Continuous" "Floor")
    (list "A-FLOR-CSWK" 3 "Continuous" "Floor: casework")
    (list "A-FLOR-EVTR" 3 "Continuous" "Floor: elevator cars and equipment")
    (list "A-FLOR-FIXT" 3 "Continuous" "Floor: fixtures (plumbing)")
    (list "A-FLOR-HRAL" 3 "Continuous" "Floor: handrails/guard rails")
    (list "A-FLOR-LEVL" 2 "Continuous" "Floor: level changes (ramps, pits, depressions)")
    (list "A-FLOR-OTLN" 243 "Continuous" "Floor: outline")
    (list "A-FLOR-OVHD" 2 "HIDDEN2" "Floor: overhead")
    (list "A-FLOR-RAIS" 3 "Continuous" "Floor: raised")
    (list "A-FLOR-RISR" 3 "Continuous" "Floor: risers")
    (list "A-FLOR-SIGN" 2 "Continuous" "Floor: signage")
    (list "A-FLOR-SPCL" 3 "Continuous" "Floor: specialties (toilet room accessories, display cases)")
    (list "A-FLOR-STRS" 3 "Continuous" "Floor: stair treads (escalators, ladders)")
    (list "A-FLOR-TPTN" 3 "Continuous" "Floor: toilet partitions")
    (list "A-FLOR-WDWK" 3 "Continuous" "Floor: architectural woodwork")
    (list "A-FURN" 8 "Continuous" "Furnishings")
    (list "A-FURN-FILE" 8 "Continuous" "Furnishings: file cabinets")
    (list "A-FURN-FIXD" 8 "Continuous" "Furnishings: fixed")
    (list "A-FURN-FREE" 8 "Continuous" "Furnishings: freestanding")
    (list "A-FURN-PLNT" 8 "Continuous" "Furnishings: plants")
    (list "A-FURN-PNLS" 8 "Continuous" "Furnishings: system panels")
    (list "A-FURN-SEAT" 8 "Continuous" "Furnishings: seating")
    (list "A-FURN-STOR" 8 "Continuous" "Furnishings: storage (component system)")
    (list "A-FURN-WKSF" 8 "Continuous" "Furnishings: work surface (component system)")
    (list "A-GLAZ" 4 "Continuous" "Glazing")
    (list "A-GLAZ-FULL" 4 "Continuous" "Glazing: full-height")
    (list "A-GLAZ-PRHT" 4 "Continuous" "Glazing: partial-height")
    (list "A-GLAZ-SILL" 3 "Continuous" "Glazing: window sills")
    (list "A-HVAC" 4 "Continuous" "HVAC systems")
    (list "A-HVAC-RDFF" 4 "Continuous" "HVAC systems: return air diffusers")
    (list "A-HVAC-SDFF" 4 "Continuous" "HVAC systems: supply diffusers")
    (list "A-LITE" 3 "Continuous" "Lighting")
    (list "A-ROOF" 243 "Continuous" "Roof")
    (list "A-ROOF-HRAL" 3 "Continuous" "Roof: handrails/guard rails")
    (list "A-ROOF-LEVL" 2 "Continuous" "Roof: level changes")
    (list "A-ROOF-OTLN" 243 "Continuous" "Roof: outline")
    (list "A-ROOF-RISR" 3 "Continuous" "Roof: risers")
    (list "A-ROOF-STRS" 3 "Continuous" "Roof: stair treads (ladders)")
    (list "A-WALL" 243 "Continuous" "Walls")
    (list "A-WALL-CAVI" 5 "Continuous" "Walls: cavity")
    (list "A-WALL-CNTR" 2 "CENTER2" "Walls: center")
    (list "A-WALL-CURT" 243 "Continuous" "Walls: curtain")
    (list "A-WALL-FIRE" 243 "Continuous" "Walls: fire protection")
    (list "A-WALL-FULL" 243 "Continuous" "Walls: full-height")
    (list "A-WALL-FULL-EXTR" 243 "Continuous" "Walls: full-height: exterior")
    (list "A-WALL-FULL-INTR" 243 "Continuous" "Walls: full-height: interior")
    (list "A-WALL-HEAD" 4 "Continuous" "Walls: door and window headers")
    (list "A-WALL-JAMB" 3 "Continuous" "Walls: door and window jambs")
    (list "A-WALL-MESH" 3 "Continuous" "Walls: mesh or wire")
    (list "A-WALL-MOVE" 3 "Continuous" "Walls: moveable")
    (list "A-WALL-PATT" 238 "Continuous" "Walls: texture and hatch patterns")
    (list "A-WALL-PRHT" 3 "Continuous" "Walls: partial-height")
  )
)

(setq *layers-C*
  (list
    (list "C-AFLD" 12 "Continuous" "Airfields")
    (list "C-AFLD-ASPH" 12 "Continuous" "Airfields: asphalt")
    (list "C-AFLD-CNTR" 11 "CENTER2" "Airfields: center")
    (list "C-AFLD-CONC" 12 "Continuous" "Airfields: concrete")
    (list "C-AFLD-FLNE" 1 "Continuous" "Airfields: fire lane")
    (list "C-AFLD-FLNE-MRKG" 2 "Continuous" "Airfields: fire lane: pavement markings")
    (list "C-AFLD-FLNE-SIGN" 2 "Continuous" "Airfields: fire lane: signage")
    (list "C-AFLD-GRVL" 12 "Continuous" "Airfields: gravel")
    (list "C-AFLD-MRKG" 2 "Continuous" "Airfields: pavement markings")
    (list "C-AFLD-SIGN" 2 "Continuous" "Airfields: signage")
    (list "C-AFLD-STAN" 2 "Continuous" "Airfields: stationing")
    (list "C-AFLD-WHIT" 7 "Continuous" "Airfields: white paint")
    (list "C-AFLD-WHIT-TICK" 7 "Continuous" "Airfields: white paint: tick marks")
    (list "C-AFLD-YELO" 2 "Continuous" "Airfields: yellow paint")
    (list "C-AFLD-YELO-TICK" 2 "Continuous" "Airfields: yellow paint: tick marks")
    (list "C-BLDG" 13 "Continuous" "Buildings and primary structures")
    (list "C-BLDG-DECK" 12 "Continuous" "Buildings and primary structures: deck")
    (list "C-BLDG-OTLN" 13 "Continuous" "Buildings and primary structures: outline")
    (list "C-BLDG-OVHD" 12 "HIDDEN2" "Buildings and primary structures: overhead")
    (list "C-BLDG-PRCH" 12 "Continuous" "Buildings and primary structures: porch")
    (list "C-BLIN" 11 "Continuous" "Baseline")
    (list "C-BLIN-STAN" 11 "Continuous" "Baseline: stationing")
    (list "C-BORE" 11 "Continuous" "Borings")
    (list "C-BRDG" 13 "Continuous" "Bridge")
    (list "C-BRDG-CNTJ" 11 "Continuous" "Bridge: construction joint")
    (list "C-BRDG-CNTR" 11 "CENTER2" "Bridge: center")
    (list "C-BRDG-DECK" 12 "Continuous" "Bridge: deck")
    (list "C-BRDG-EXPJ" 11 "Continuous" "Bridge: expansion joint")
    (list "C-BRDG-FALT" 11 "Continuous" "Bridge: fault/break line")
    (list "C-BRDG-HIDD" 11 "HIDDEN2" "Bridge: objects or lines hidden from view")
    (list "C-BRDG-OBJT" 12 "Continuous" "Bridge: objects")
    (list "C-BRDG-OBJT-PRIM" 13 "Continuous" "Bridge: objects: primary")
    (list "C-BRDG-OBJT-SECD" 12 "Continuous" "Bridge: objects: secondary")
    (list "C-BRDG-RBAR" 11 "Continuous" "Bridge: reinforcing bar")
    (list "C-CATV" 4 "Continuous" "Cable television system")
    (list "C-CATV-OVHD" 4 "HIDDEN2" "Cable television system: overhead")
    (list "C-CATV-POLE" 4 "Continuous" "Cable television system: pole")
    (list "C-CATV-UGND" 4 "HIDDEN2" "Cable television system: underground")
    (list "C-CEME" 11 "Continuous" "Cemetery")
    (list "C-CHAN" 13 "Continuous" "Navigable channels")
    (list "C-CHAN-BWTR" 13 "Continuous" "Navigable channels: breakwater")
    (list "C-CHAN-CNTR" 11 "CENTER2" "Navigable channels: center")
    (list "C-CHAN-DACL" 11 "Continuous" "Navigable channels: de-authorized channel limits")
    (list "C-CHAN-DOCK" 12 "Continuous" "Navigable channels: decks, docks, floats, piers")
    (list "C-CHAN-NAID" 2 "Continuous" "Navigable channels: navigation aids")
    (list "C-COMM" 4 "Continuous" "Communications")
    (list "C-COMM-OVHD" 4 "HIDDEN2" "Communications: overhead")
    (list "C-COMM-POLE" 4 "Continuous" "Communications: pole")
    (list "C-COMM-UGND" 4 "HIDDEN2" "Communications: underground")
    (list "C-CTRL" 11 "Continuous" "Control points")
    (list "C-CTRL-BMRK" 11 "Continuous" "Control points: benchmarks")
    (list "C-CTRL-FLYS" 11 "Continuous" "Control points: fly station")
    (list "C-CTRL-GRID" 11 "CENTER2" "Control points: grid")
    (list "C-CTRL-HORZ" 11 "Continuous" "Control points: horizontal")
    (list "C-CTRL-HVPT" 11 "Continuous" "Control points: horizontal/vertical")
    (list "C-CTRL-PNPT" 11 "Continuous" "Control points: panel points")
    (list "C-CTRL-TRAV" 11 "Continuous" "Control points: transverse")
    (list "C-CTRL-VERT" 11 "Continuous" "Control points: vertical")
    (list "C-DFLD" 12 "Continuous" "Drain fields")
    (list "C-DFLD-OTLN" 12 "Continuous" "Drain fields: outline")
    (list "C-DFLD-PROF" 11 "Continuous" "Drain fields: profile")
    (list "C-DRIV" 12 "Continuous" "Driveways")
    (list "C-DRIV-ASPH" 12 "Continuous" "Driveways: asphalt")
    (list "C-DRIV-CNTR" 11 "CENTER2" "Driveways: center")
    (list "C-DRIV-CONC" 12 "Continuous" "Driveways: concrete")
    (list "C-DRIV-CURB" 13 "Continuous" "Driveways: curb")
    (list "C-DRIV-CURB-BACK" 12 "Continuous" "Driveways: curb: back")
    (list "C-DRIV-CURB-FACE" 13 "Continuous" "Driveways: curb: face")
    (list "C-DRIV-FLNE" 1 "Continuous" "Driveways: fire lane")
    (list "C-DRIV-FLNE-MRKG" 2 "Continuous" "Driveways: fire lane: pavement markings")
    (list "C-DRIV-FLNE-SIGN" 2 "Continuous" "Driveways: fire lane: signage")
    (list "C-DRIV-GRVL" 12 "Continuous" "Driveways: gravel")
    (list "C-DRIV-MRKG" 2 "Continuous" "Driveways: pavement markings")
    (list "C-DRIV-SIGN" 2 "Continuous" "Driveways: signage")
    (list "C-DRIV-UPVD" 11 "Continuous" "Driveways: unpaved surface")
    (list "C-DRIV-WHIT" 7 "Continuous" "Driveways: white paint")
    (list "C-DRIV-WHIT-TICK" 7 "Continuous" "Driveways: white paint: tick marks")
    (list "C-DRIV-YELO" 2 "Continuous" "Driveways: yellow paint")
    (list "C-DRIV-YELO-TICK" 2 "Continuous" "Driveways: yellow paint: tick marks")
    (list "C-DTCH" 13 "Continuous" "Ditches or washes")
    (list "C-DTCH-BOTM" 11 "Continuous" "Ditches or washes: bottom")
    (list "C-DTCH-CNTR" 11 "CENTER2" "Ditches or washes: center")
    (list "C-DTCH-EWAT" 11 "Continuous" "Ditches or washes: edge of water")
    (list "C-DTCH-TOP" 12 "Continuous" "Ditches or washes: top")
    (list "C-EROS" 11 "Continuous" "Erosion and sediment control")
    (list "C-EROS-CIPR" 11 "Continuous" "Erosion and sediment control: culvert inlet protection")
    (list "C-EROS-CNTE" 11 "Continuous" "Erosion and sediment control: construction entrance")
    (list "C-EROS-DDIV" 11 "Continuous" "Erosion and sediment control: drainage divides")
    (list "C-EROS-DVDK" 11 "Continuous" "Erosion and sediment control: diversion dike")
    (list "C-EROS-INPR" 11 "Continuous" "Erosion and sediment control: inlet protection")
    (list "C-EROS-SILT" 11 "Continuous" "Erosion and sediment control: silt fence")
    (list "C-EROS-SSLT" 11 "Continuous" "Erosion and sediment control: super silt fence")
    (list "C-ESMT" 2 "DASHED2" "Easements")
    (list "C-ESMT-ACCS" 2 "DASHED2" "Easements: access")
    (list "C-ESMT-CATV" 2 "DASHED2" "Easements: utility - cable television system")
    (list "C-ESMT-CONS" 2 "DASHED2" "Easements: conservation")
    (list "C-ESMT-CSTG" 2 "DASHED2" "Easements: construction/grading")
    (list "C-ESMT-ELEC" 2 "DASHED2" "Easements: electrical")
    (list "C-ESMT-FDPL" 2 "DASHED2" "Easements: flood plain")
    (list "C-ESMT-INEG" 2 "DASHED2" "Easements: ingress/egress")
    (list "C-ESMT-LSCP" 2 "DASHED2" "Easements: landscape")
    (list "C-ESMT-NGAS" 2 "DASHED2" "Easements: natural gas line")
    (list "C-ESMT-PHON" 2 "DASHED2" "Easements: telephone line")
    (list "C-ESMT-ROAD" 2 "DASHED2" "Easements: roadway")
    (list "C-ESMT-ROAD-PERM" 2 "DASHED2" "Easements: roadway: permanent")
    (list "C-ESMT-ROAD-TEMP" 2 "DASHED2" "Easements: roadway: temporary")
    (list "C-ESMT-RWAY" 2 "DASHED2" "Easements: right-of-way (public access)")
    (list "C-ESMT-SGHT" 2 "DASHED2" "Easements: sight distance")
    (list "C-ESMT-SSWR" 2 "DASHED2" "Easements: sanitary sewer")
    (list "C-ESMT-STRM" 2 "DASHED2" "Easements: storm sewer")
    (list "C-ESMT-SWMT" 2 "DASHED2" "Easements: storm water management")
    (list "C-ESMT-TRAL" 2 "DASHED2" "Easements: trail or path")
    (list "C-ESMT-UTIL" 2 "DASHED2" "Easements: utility lines")
    (list "C-ESMT-WATR" 2 "DASHED2" "Easements: water supply")
    (list "C-FENC" 12 "Continuous" "Fences")
    (list "C-FENC-GRAL" 12 "Continuous" "Fences: guard rail")
    (list "C-FENC-POST" 12 "Continuous" "Fences: posts")
    (list "C-FENC-STEL" 12 "Continuous" "Fences: steel (barbed wire and/or chain link)")
    (list "C-FENC-WOOD" 12 "Continuous" "Fences: wood")
    (list "C-FIRE" 1 "Continuous" "Fire protection")
    (list "C-FIRE-HYDT" 1 "Continuous" "Fire protection: hydrants and connections")
    (list "C-FIRE-PIPE" 1 "Continuous" "Fire protection: piping")
    (list "C-FIRE-UGND" 1 "HIDDEN2" "Fire protection: underground")
    (list "C-FLHA" 11 "Continuous" "Flood hazard area")
    (list "C-FLHA-025Y" 11 "Continuous" "Flood hazard area: 25 year mark")
    (list "C-FLHA-050Y" 11 "Continuous" "Flood hazard area: 50 year mark")
    (list "C-FLHA-100Y" 11 "Continuous" "Flood hazard area: 100 year mark")
    (list "C-FLHA-200Y" 11 "Continuous" "Flood hazard area: 200 year mark")
    (list "C-FUEL" 4 "Continuous" "Fuel systems")
    (list "C-FUEL-EQPM" 4 "Continuous" "Fuel systems: equipment")
    (list "C-FUEL-INST" 4 "Continuous" "Fuel systems: instrumentation")
    (list "C-FUEL-MHOL" 4 "Continuous" "Fuel systems: manhole")
    (list "C-FUEL-PIPE" 4 "Continuous" "Fuel systems: piping")
    (list "C-FUEL-TANK" 4 "Continuous" "Fuel systems: storage tanks")
    (list "C-FUEL-UGND" 4 "HIDDEN2" "Fuel systems: underground")
    (list "C-HYDR" 13 "Continuous" "Hydraulic structure")
    (list "C-HYDR-BAFL" 12 "Continuous" "Hydraulic structure: baffle block and splash pad")
    (list "C-HYDR-BASN" 12 "Continuous" "Hydraulic structure: stilling and settling basins")
    (list "C-HYDR-CNDT" 12 "Continuous" "Hydraulic structure: diversion/bypass conduits/culverts")
    (list "C-HYDR-COFF" 12 "Continuous" "Hydraulic structure: coffer dam")
    (list "C-HYDR-DAM" 13 "Continuous" "Hydraulic structure: dam")
    (list "C-HYDR-FISH" 12 "Continuous" "Hydraulic structure: fish ladder/passage")
    (list "C-HYDR-FLUM" 12 "Continuous" "Hydraulic structure: flume")
    (list "C-HYDR-INTK" 12 "Continuous" "Hydraulic structure: intake")
    (list "C-HYDR-NOVR" 12 "Continuous" "Hydraulic structure: non-overflow structure")
    (list "C-HYDR-PENS" 12 "Continuous" "Hydraulic structure: penstock")
    (list "C-LOCN" 6 "Continuous" "Limits of construction")
    (list "C-NGAS" 4 "Continuous" "Natural gas systems")
    (list "C-NGAS-EQPM" 4 "Continuous" "Natural gas systems: equipment")
    (list "C-NGAS-INST" 4 "Continuous" "Natural gas systems: instrumentation")
    (list "C-NGAS-MHOL" 4 "Continuous" "Natural gas systems: manhole")
    (list "C-NGAS-PIPE" 4 "Continuous" "Natural gas systems: piping")
    (list "C-NGAS-TANK" 4 "Continuous" "Natural gas systems: storage tanks")
    (list "C-NGAS-UGND" 4 "HIDDEN2" "Natural gas systems: underground")
    (list "C-PERC" 11 "Continuous" "Perc testing")
    (list "C-PERC-HOLE" 11 "Continuous" "Perc testing: holes")
    (list "C-POND" 13 "Continuous" "Ponds")
    (list "C-POND-EDGE" 13 "Continuous" "Ponds: edge")
    (list "C-POND-SWAY" 13 "Continuous" "Ponds: spillway")
    (list "C-POND-TOPB" 12 "Continuous" "Ponds: top of bank")
    (list "C-POWR" 4 "Continuous" "Power")
    (list "C-POWR-FENC" 4 "Continuous" "Power: fences")
    (list "C-POWR-INST" 4 "Continuous" "Power: instrumentation")
    (list "C-POWR-MHOL" 4 "Continuous" "Power: manhole")
    (list "C-POWR-OVHD" 4 "HIDDEN2" "Power: overhead")
    (list "C-POWR-POLE" 4 "Continuous" "Power: pole")
    (list "C-POWR-STRC" 4 "Continuous" "Power: structures")
    (list "C-POWR-UGND" 4 "HIDDEN2" "Power: underground")
    (list "C-PRKG" 12 "Continuous" "Parking lots")
    (list "C-PRKG-ASPH" 12 "Continuous" "Parking lots: asphalt")
    (list "C-PRKG-CARS" 8 "Continuous" "Parking lots: cars and other vehicles")
    (list "C-PRKG-CONC" 12 "Continuous" "Parking lots: concrete")
    (list "C-PRKG-CURB" 13 "Continuous" "Parking lots: curb")
    (list "C-PRKG-CURB-BACK" 12 "Continuous" "Parking lots: curb: back")
    (list "C-PRKG-CURB-FACE" 13 "Continuous" "Parking lots: curb: face")
    (list "C-PRKG-DRAN" 11 "Continuous" "Parking lots: drainage slope indications")
    (list "C-PRKG-FIXT" 12 "Continuous" "Parking lots: fixtures")
    (list "C-PRKG-FLNE" 1 "Continuous" "Parking lots: fire lane")
    (list "C-PRKG-FLNE-MRKG" 2 "Continuous" "Parking lots: fire lane: pavement markings")
    (list "C-PRKG-FLNE-SIGN" 2 "Continuous" "Parking lots: fire lane: signage")
    (list "C-PRKG-GRVL" 12 "Continuous" "Parking lots: gravel")
    (list "C-PRKG-MRKG" 2 "Continuous" "Parking lots: pavement markings")
    (list "C-PRKG-SIGN" 2 "Continuous" "Parking lots: signage")
    (list "C-PRKG-STRP" 2 "Continuous" "Parking lots: striping")
    (list "C-PRKG-UPVD" 11 "Continuous" "Parking lots: unpaved surface")
    (list "C-PRKG-WHIT" 7 "Continuous" "Parking lots: white paint")
    (list "C-PRKG-WHIT-TICK" 7 "Continuous" "Parking lots: white paint: tick marks")
    (list "C-PRKG-YELO" 2 "Continuous" "Parking lots: yellow paint")
    (list "C-PRKG-YELO-TICK" 2 "Continuous" "Parking lots: yellow paint: tick marks")
    (list "C-PROP" 6 "Continuous" "Property")
    (list "C-PROP-LINE" 6 "Continuous" "Property: lines")
    (list "C-PROP-SBCK" 2 "DASHED2" "Property: setback lines")
    (list "C-PVMT" 12 "Continuous" "Pavement")
    (list "C-PVMT-ASPH" 12 "Continuous" "Pavement: asphalt")
    (list "C-PVMT-CONC" 12 "Continuous" "Pavement: concrete")
    (list "C-PVMT-GRVL" 12 "Continuous" "Pavement: gravel")
    (list "C-RAIL" 13 "Continuous" "Railroad")
    (list "C-RAIL-CNTR" 11 "CENTER2" "Railroad: center")
    (list "C-RAIL-EQPM" 4 "Continuous" "Railroad: equipment")
    (list "C-RAIL-TRAK" 13 "Continuous" "Railroad: track")
    (list "C-RIVR" 13 "Continuous" "River")
    (list "C-RIVR-BOTM" 11 "Continuous" "River: bottom")
    (list "C-RIVR-CNTR" 11 "CENTER2" "River: center")
    (list "C-RIVR-EDGE" 13 "Continuous" "River: edge")
    (list "C-RIVR-TOPB" 12 "Continuous" "River: top of bank")
    (list "C-ROAD" 13 "Continuous" "Roadways")
    (list "C-ROAD-ASPH" 12 "Continuous" "Roadways: asphalt")
    (list "C-ROAD-CNTR" 11 "CENTER2" "Roadways: center")
    (list "C-ROAD-CONC" 12 "Continuous" "Roadways: concrete")
    (list "C-ROAD-CURB" 13 "Continuous" "Roadways: curb")
    (list "C-ROAD-CURB-BACK" 12 "Continuous" "Roadways: curb: back")
    (list "C-ROAD-CURB-FACE" 13 "Continuous" "Roadways: curb: face")
    (list "C-ROAD-FLNE" 1 "Continuous" "Roadways: fire lane")
    (list "C-ROAD-FLNE-MRKG" 2 "Continuous" "Roadways: fire lane: pavement markings")
    (list "C-ROAD-FLNE-SIGN" 2 "Continuous" "Roadways: fire lane: signage")
    (list "C-ROAD-GRVL" 12 "Continuous" "Roadways: gravel")
    (list "C-ROAD-MRKG" 2 "Continuous" "Roadways: pavement markings")
    (list "C-ROAD-PROF" 11 "Continuous" "Roadways: profile")
    (list "C-ROAD-SIGN" 2 "Continuous" "Roadways: signage")
    (list "C-ROAD-STAN" 2 "Continuous" "Roadways: stationing")
    (list "C-ROAD-UPVD" 11 "Continuous" "Roadways: unpaved surface")
    (list "C-ROAD-WHIT" 7 "Continuous" "Roadways: white paint")
    (list "C-ROAD-WHIT-TICK" 7 "Continuous" "Roadways: white paint: tick marks")
    (list "C-ROAD-YELO" 2 "Continuous" "Roadways: yellow paint")
    (list "C-ROAD-YELO-TICK" 2 "Continuous" "Roadways: yellow paint: tick marks")
    (list "C-RRAP" 12 "Continuous" "Riprap")
    (list "C-SGHT" 11 "Continuous" "Sight distance")
    (list "C-SGHT-PROF" 11 "Continuous" "Sight distance: profile")
    (list "C-SOIL" 1 "Continuous" "Soils")
    (list "C-SSWR" 4 "Continuous" "Sanitary sewer")
    (list "C-SSWR-DIAG" 2 "Continuous" "Sanitary sewer: diagrams")
    (list "C-SSWR-FORC" 4 "Continuous" "Sanitary sewer: force main")
    (list "C-SSWR-LATL" 4 "Continuous" "Sanitary sewer: lateral line")
    (list "C-SSWR-MHOL" 4 "Continuous" "Sanitary sewer: manhole")
    (list "C-SSWR-PIPE" 4 "Continuous" "Sanitary sewer: piping")
    (list "C-SSWR-PIPE-RCON" 4 "Continuous" "Sanitary sewer: piping: reinforced concrete")
    (list "C-SSWR-PIPE-STEL" 4 "Continuous" "Sanitary sewer: piping: steel")
    (list "C-SSWR-PROF" 11 "Continuous" "Sanitary sewer: profile")
    (list "C-SSWR-STAN" 2 "Continuous" "Sanitary sewer: stationing")
    (list "C-SSWR-STRC" 12 "Continuous" "Sanitary sewer: structures")
    (list "C-SSWR-UGND" 4 "HIDDEN2" "Sanitary sewer: underground")
    (list "C-STEM" 4 "Continuous" "Steam system")
    (list "C-STEM-INST" 4 "Continuous" "Steam system: instrumentation")
    (list "C-STEM-MHOL" 4 "Continuous" "Steam system: manhole")
    (list "C-STEM-PIPE" 4 "Continuous" "Steam system: piping")
    (list "C-STEM-STRC" 12 "Continuous" "Steam system: structures")
    (list "C-STEM-UGND" 4 "HIDDEN2" "Steam system: underground")
    (list "C-STRM" 4 "Continuous" "Storm sewer")
    (list "C-STRM-CNTR" 11 "CENTER2" "Storm sewer: center")
    (list "C-STRM-DIAG" 2 "Continuous" "Storm sewer: diagrams")
    (list "C-STRM-HWAL" 12 "Continuous" "Storm sewer: headwall")
    (list "C-STRM-MHOL" 4 "Continuous" "Storm sewer: manhole")
    (list "C-STRM-PIPE" 4 "Continuous" "Storm sewer: piping")
    (list "C-STRM-PIPE-CMTL" 4 "Continuous" "Storm sewer: piping: corrugated metal")
    (list "C-STRM-PIPE-RCON" 4 "Continuous" "Storm sewer: piping: reinforced concrete")
    (list "C-STRM-PROF" 11 "Continuous" "Storm sewer: profile")
    (list "C-STRM-STAN" 2 "Continuous" "Storm sewer: stationing")
    (list "C-STRM-STRC" 12 "Continuous" "Storm sewer: structures")
    (list "C-STRM-UGND" 4 "HIDDEN2" "Storm sewer: underground")
    (list "C-SWLK" 12 "Continuous" "Sidewalks")
    (list "C-SWLK-ASPH" 12 "Continuous" "Sidewalks: asphalt")
    (list "C-SWLK-CONC" 12 "Continuous" "Sidewalks: concrete")
    (list "C-TINN" 11 "Continuous" "Triangulated irregular network")
    (list "C-TINN-BNDY" 11 "Continuous" "Triangulated irregular network: boundary")
    (list "C-TINN-FALT" 11 "Continuous" "Triangulated irregular network: fault/break lines")
    (list "C-TINN-VIEW" 11 "Continuous" "Triangulated irregular network: triangulation view")
    (list "C-TINN-VOID" 11 "Continuous" "Triangulated irregular network: void regions")
    (list "C-TOPO" 12 "Continuous" "Topographic feature")
    (list "C-TOPO-DEPR" 11 "Continuous" "Topographic feature: depression")
    (list "C-TOPO-MAJR" 13 "Continuous" "Topographic feature: major (contours)")
    (list "C-TOPO-MINR" 11 "Continuous" "Topographic feature: minor (contours)")
    (list "C-TOPO-SPOT" 2 "Continuous" "Topographic feature: spot elevations")
    (list "C-TOPO-TPIT" 11 "Continuous" "Topographic feature: test pits")
    (list "C-TRAL" 12 "Continuous" "Trails or paths")
    (list "C-TRAL-ASPH" 12 "Continuous" "Trails or paths: asphalt")
    (list "C-TRAL-CONC" 12 "Continuous" "Trails or paths: concrete")
    (list "C-TRAL-GRVL" 12 "Continuous" "Trails or paths: gravel")
    (list "C-TRAL-MRKG" 2 "Continuous" "Trails or paths: pavement markings")
    (list "C-TRAL-SIGN" 2 "Continuous" "Trails or paths: signage")
    (list "C-TRAL-UPVD" 11 "Continuous" "Trails or paths: unpaved surface")
    (list "C-WALL" 13 "Continuous" "Walls")
    (list "C-WALL-CTLJ" 11 "Continuous" "Walls: control joint")
    (list "C-WALL-NSBR" 13 "Continuous" "Walls: noise barrier")
    (list "C-WALL-RTWL" 13 "Continuous" "Walls: retaining wall")
    (list "C-WALL-SHEA" 13 "Continuous" "Walls: structural bearing or shear walls")
    (list "C-WATR" 4 "Continuous" "Water supply")
    (list "C-WATR-DIAG" 2 "Continuous" "Water supply: diagrams")
    (list "C-WATR-INST" 4 "Continuous" "Water supply: instrumentation")
    (list "C-WATR-PIPE" 4 "Continuous" "Water supply: piping")
    (list "C-WATR-PROF" 11 "Continuous" "Water supply: profile")
    (list "C-WATR-STAN" 2 "Continuous" "Water supply: stationing")
    (list "C-WATR-STRC" 12 "Continuous" "Water supply: structures")
    (list "C-WATR-UGND" 4 "HIDDEN2" "Water supply: underground")
    (list "C-WATR-WELL" 4 "Continuous" "Water supply: well")
    (list "C-WETL" 13 "Continuous" "Wetlands")
    (list "C-WWAY" 13 "Continuous" "Waterway")
    (list "C-WWAY-DLPH" 12 "Continuous" "Waterway: dolphin")
    (list "C-WWAY-FEND" 12 "Continuous" "Waterway: fender")
    (list "C-WWAY-MOOR" 12 "Continuous" "Waterway: mooring")
  )
)

(setq *layers-E*
  (list
    (list "E-ALRM" 1 "Continuous" "Alarm system")
    (list "E-AREA" 2 "Continuous" "Area")
    (list "E-AREA-OFST" 2 "Continuous" "Area: offset zones")
    (list "E-AREA-SHAD" 2 "Continuous" "Area: shade zones")
    (list "E-AUXL" 4 "Continuous" "Auxiliary systems")
    (list "E-BELL" 4 "Continuous" "Bell system")
    (list "E-CABL" 4 "Continuous" "Cable systems")
    (list "E-CABL-COAX" 4 "Continuous" "Cable systems: coax cable")
    (list "E-CABL-FIBR" 4 "Continuous" "Cable systems: fiber optics cable")
    (list "E-CABL-MULT" 4 "Continuous" "Cable systems: multi-conductor cable")
    (list "E-CABL-TRAY" 4 "Continuous" "Cable systems: cabletray and wireways")
    (list "E-CATH" 4 "Continuous" "Cathodic protection system")
    (list "E-CATH-ANOD" 4 "Continuous" "Cathodic protection system: sacrificial anode")
    (list "E-CATH-CURR" 4 "Continuous" "Cathodic protection system: impress current")
    (list "E-CATH-TEST" 4 "Continuous" "Cathodic protection system: test stations")
    (list "E-CCTV" 4 "Continuous" "Closed-circuit television system")
    (list "E-CLOK" 4 "Continuous" "Clock system")
    (list "E-CLOK-CIRC" 4 "Continuous" "Clock system: circuits")
    (list "E-CLOK-CLNG" 30 "Continuous" "Clock system: ceiling")
    (list "E-CLOK-CNMB" 2 "Continuous" "Clock system: circuit number")
    (list "E-CLOK-EQPM" 4 "Continuous" "Clock system: equipment")
    (list "E-CLOK-FLOR" 2 "Continuous" "Clock system: floor")
    (list "E-CLOK-WALL" 4 "Continuous" "Clock system: wall")
    (list "E-COMM" 4 "Continuous" "Communications")
    (list "E-COMM-CIRC" 4 "Continuous" "Communications: circuits")
    (list "E-COMM-CLNG" 30 "Continuous" "Communications: ceiling")
    (list "E-COMM-CNMB" 2 "Continuous" "Communications: circuit number")
    (list "E-COMM-EQPM" 4 "Continuous" "Communications: equipment")
    (list "E-COMM-WALL" 4 "Continuous" "Communications: wall")
    (list "E-CONT" 4 "Continuous" "Controls and instrumentation")
    (list "E-CONT-DEVC" 4 "Continuous" "Controls and instrumentation: devices")
    (list "E-CONT-WIRE" 4 "Continuous" "Controls and instrumentation: wiring")
    (list "E-DATA" 4 "Continuous" "Data/LAN system")
    (list "E-DATA-CIRC" 4 "Continuous" "Data/LAN system: circuits")
    (list "E-DATA-CLNG" 30 "Continuous" "Data/LAN system: ceiling")
    (list "E-DATA-CNMB" 2 "Continuous" "Data/LAN system: circuit number")
    (list "E-DATA-EQPM" 4 "Continuous" "Data/LAN system: equipment")
    (list "E-DATA-FLOR" 2 "Continuous" "Data/LAN system: floor")
    (list "E-DATA-WALL" 4 "Continuous" "Data/LAN system: wall")
    (list "E-DIAG" 2 "Continuous" "Diagrams")
    (list "E-DIAG-BKRS" 2 "Continuous" "Diagrams: breakers")
    (list "E-DIAG-BUSS" 2 "Continuous" "Diagrams: bus duct")
    (list "E-DIAG-ENCL" 2 "Continuous" "Diagrams: equipment enclosures")
    (list "E-DIAG-EQPM" 2 "Continuous" "Diagrams: equipment")
    (list "E-DIAG-FEED" 2 "Continuous" "Diagrams: feeders")
    (list "E-DIAG-FLOR" 2 "Continuous" "Diagrams: floor")
    (list "E-DIAG-GRND" 2 "Continuous" "Diagrams: ground")
    (list "E-DIAG-SWCH" 2 "Continuous" "Diagrams: switches")
    (list "E-DIAG-XFMR" 2 "Continuous" "Diagrams: transformers")
    (list "E-DICT" 4 "Continuous" "Dictation system")
    (list "E-DICT-CIRC" 4 "Continuous" "Dictation system: circuits")
    (list "E-DICT-CLNG" 30 "Continuous" "Dictation system: ceiling")
    (list "E-DICT-CNMB" 2 "Continuous" "Dictation system: circuit number")
    (list "E-DICT-EQPM" 4 "Continuous" "Dictation system: equipment")
    (list "E-DICT-WALL" 4 "Continuous" "Dictation system: wall")
    (list "E-FIRE" 1 "Continuous" "Fire protection")
    (list "E-FIRE-BARR" 1 "Continuous" "Fire protection: barrier")
    (list "E-FIRE-CIRC" 1 "Continuous" "Fire protection: circuits")
    (list "E-FIRE-CLNG" 30 "Continuous" "Fire protection: ceiling")
    (list "E-FIRE-CNMB" 1 "Continuous" "Fire protection: circuit number")
    (list "E-FIRE-EQPM" 1 "Continuous" "Fire protection: equipment")
    (list "E-FIRE-WALL" 1 "Continuous" "Fire protection: wall")
    (list "E-GRND" 4 "Continuous" "Ground system")
    (list "E-GRND-CIRC" 4 "Continuous" "Ground system: circuits")
    (list "E-GRND-CLNG" 30 "Continuous" "Ground system: ceiling")
    (list "E-GRND-CNMB" 2 "Continuous" "Ground system: circuit number")
    (list "E-GRND-DIAG" 2 "Continuous" "Ground system: diagrams")
    (list "E-GRND-EQPM" 4 "Continuous" "Ground system: equipment")
    (list "E-GRND-EQUI" 4 "Continuous" "Ground system: equipotential")
    (list "E-GRND-WALL" 4 "Continuous" "Ground system: wall")
    (list "E-INST" 4 "Continuous" "Instrumentation system")
    (list "E-INST-CIRC" 4 "Continuous" "Instrumentation system: circuits")
    (list "E-INST-CLNG" 30 "Continuous" "Instrumentation system: ceiling")
    (list "E-INST-CNMB" 2 "Continuous" "Instrumentation system: circuit number")
    (list "E-INST-EQPM" 4 "Continuous" "Instrumentation system: equipment")
    (list "E-INST-WALL" 4 "Continuous" "Instrumentation system: wall")
    (list "E-INTC" 4 "Continuous" "Intercom/PA systems")
    (list "E-LITE" 3 "Continuous" "Lighting")
    (list "E-LITE-CIRC" 3 "Continuous" "Lighting: circuits")
    (list "E-LITE-CIRC-CRIT" 1 "Continuous" "Lighting: circuits: critical")
    (list "E-LITE-CIRC-EMER" 1 "Continuous" "Lighting: circuits: emergency")
    (list "E-LITE-CLNG" 30 "Continuous" "Lighting: ceiling")
    (list "E-LITE-CLNG-CRIT" 1 "Continuous" "Lighting: ceiling: critical")
    (list "E-LITE-CLNG-EMER" 1 "Continuous" "Lighting: ceiling: emergency")
    (list "E-LITE-CLNG-EXIT" 1 "Continuous" "Lighting: ceiling: exit")
    (list "E-LITE-CNMB" 2 "Continuous" "Lighting: circuit number")
    (list "E-LITE-CNMB-CRIT" 2 "Continuous" "Lighting: circuit number: critical")
    (list "E-LITE-CNMB-EMER" 2 "Continuous" "Lighting: circuit number: emergency")
    (list "E-LITE-EMER" 1 "Continuous" "Lighting: emergency")
    (list "E-LITE-EQPM" 3 "Continuous" "Lighting: equipment")
    (list "E-LITE-EQPM-CRIT" 1 "Continuous" "Lighting: equipment: critical")
    (list "E-LITE-EQPM-EMER" 1 "Continuous" "Lighting: equipment: emergency")
    (list "E-LITE-EXIT" 1 "Continuous" "Lighting: exit")
    (list "E-LITE-EXTR" 3 "Continuous" "Lighting: exterior")
    (list "E-LITE-FLOR" 2 "Continuous" "Lighting: floor")
    (list "E-LITE-JBOX" 3 "Continuous" "Lighting: junction box")
    (list "E-LITE-OTLN" 2 "Continuous" "Lighting: outline")
    (list "E-LITE-ROOF" 3 "Continuous" "Lighting: roof")
    (list "E-LITE-SPCL" 3 "Continuous" "Lighting: special")
    (list "E-LITE-SWCH" 3 "Continuous" "Lighting: switches")
    (list "E-LITE-SWCH-CRIT" 1 "Continuous" "Lighting: switches: critical")
    (list "E-LITE-SWCH-EMER" 1 "Continuous" "Lighting: switches: emergency")
    (list "E-LITE-WALL" 3 "Continuous" "Lighting: wall")
    (list "E-LITE-WALL-CRIT" 1 "Continuous" "Lighting: wall: critical")
    (list "E-LITE-WALL-EMER" 1 "Continuous" "Lighting: wall: emergency")
    (list "E-LITE-WALL-EXIT" 1 "Continuous" "Lighting: wall: exit")
    (list "E-LTNG" 4 "Continuous" "Lightning protection system")
    (list "E-LTNG-CIRC" 4 "Continuous" "Lightning protection system: circuits")
    (list "E-LTNG-CLNG" 30 "Continuous" "Lightning protection system: ceiling")
    (list "E-LTNG-CNMB" 2 "Continuous" "Lightning protection system: circuit number")
    (list "E-LTNG-EQPM" 4 "Continuous" "Lightning protection system: equipment")
    (list "E-LTNG-WALL" 4 "Continuous" "Lightning protection system: wall")
    (list "E-MNTG" 4 "Continuous" "Mounting system")
    (list "E-NURS" 4 "Continuous" "Nurse call system")
    (list "E-NURS-CIRC" 4 "Continuous" "Nurse call system: circuits")
    (list "E-NURS-CLNG" 30 "Continuous" "Nurse call system: ceiling")
    (list "E-NURS-CNMB" 2 "Continuous" "Nurse call system: circuit number")
    (list "E-NURS-EQPM" 4 "Continuous" "Nurse call system: equipment")
    (list "E-NURS-FLOR" 2 "Continuous" "Nurse call system: floor")
    (list "E-NURS-WALL" 4 "Continuous" "Nurse call system: wall")
    (list "E-OBST" 2 "Continuous" "Obstructions")
    (list "E-PGNG" 4 "Continuous" "Paging system")
    (list "E-POWR" 5 "Continuous" "Power")
    (list "E-POWR-BUSW" 5 "Continuous" "Power: busways")
    (list "E-POWR-CABL" 5 "Continuous" "Power: cable systems")
    (list "E-POWR-CBOX" 5 "Continuous" "Power: combiner box")
    (list "E-POWR-CBOX-FTPT" 2 "Continuous" "Power: combiner box: area footprints")
    (list "E-POWR-CIRC" 5 "Continuous" "Power: circuits")
    (list "E-POWR-CIRC-CRIT" 1 "Continuous" "Power: circuits: critical")
    (list "E-POWR-CLNG" 30 "Continuous" "Power: ceiling")
    (list "E-POWR-CLNG-CRIT" 1 "Continuous" "Power: ceiling: critical")
    (list "E-POWR-CNDT" 5 "Continuous" "Power: conduit")
    (list "E-POWR-CNMB" 2 "Continuous" "Power: circuit number")
    (list "E-POWR-CNMB-CRIT" 2 "Continuous" "Power: circuit number: critical")
    (list "E-POWR-DEVC" 3 "Continuous" "Power: devices")
    (list "E-POWR-DSCO" 5 "Continuous" "Power: disconnect switches")
    (list "E-POWR-DSCO-ACFU" 5 "Continuous" "Power: disconnect switches: fused ac")
    (list "E-POWR-DSCO-ACNF" 5 "Continuous" "Power: disconnect switches: unfused ac")
    (list "E-POWR-DSCO-DCFU" 5 "Continuous" "Power: disconnect switches: fused dc")
    (list "E-POWR-DSCO-DCNF" 5 "Continuous" "Power: disconnect switches: unfused dc")
    (list "E-POWR-EQPM" 5 "Continuous" "Power: equipment")
    (list "E-POWR-EQPM-CRIT" 1 "Continuous" "Power: equipment: critical")
    (list "E-POWR-EXTR" 5 "Continuous" "Power: exterior")
    (list "E-POWR-FEED" 5 "Continuous" "Power: feeders")
    (list "E-POWR-FLOR" 2 "Continuous" "Power: floor")
    (list "E-POWR-FLOR-CRIT" 1 "Continuous" "Power: floor: critical")
    (list "E-POWR-JBOX" 5 "Continuous" "Power: junction box")
    (list "E-POWR-PANL" 5 "Continuous" "Power: panels")
    (list "E-POWR-POCC" 5 "Continuous" "Power: point of common coupling")
    (list "E-POWR-POI" 5 "Continuous" "Power: point of interconnection")
    (list "E-POWR-ROOF" 5 "Continuous" "Power: roof")
    (list "E-POWR-SWBD" 5 "Continuous" "Power: switchboards")
    (list "E-POWR-UCPT" 3 "Continuous" "Power: under-carpet wiring")
    (list "E-POWR-URAC" 3 "Continuous" "Power: underfloor raceways")
    (list "E-POWR-WALL" 5 "Continuous" "Power: wall")
    (list "E-POWR-WALL-CRIT" 1 "Continuous" "Power: wall: critical")
    (list "E-POWR-XFMR-PADM" 5 "Continuous" "Power: transformers: pad-mounted")
    (list "E-POWR-XFMR-POLM" 5 "Continuous" "Power: transformers: pole-mounted")
    (list "E-PVMD" 4 "Continuous" "Photovoltaic modules")
    (list "E-SITE" 3 "Continuous" "Site features")
    (list "E-SITE-OVHD" 3 "HIDDEN2" "Site features: overhead")
    (list "E-SITE-POLE" 3 "Continuous" "Site features: pole")
    (list "E-SITE-UGND" 3 "HIDDEN2" "Site features: underground")
    (list "E-SOUN" 4 "Continuous" "Sound system")
    (list "E-UTIL" 4 "Continuous" "Utilities")
  )
)

(setq *layers-Q*
  (list
    (list "Q-CMPR" 4 "Continuous" "Computer")
    (list "Q-CSWK" 3 "Continuous" "Casework")
    (list "Q-CSWK-DVDR" 3 "Continuous" "Casework: thin dividers")
    (list "Q-CSWK-EDGE" 3 "Continuous" "Casework: edge")
    (list "Q-CSWK-ELEV" 2 "Continuous" "Casework: elevation")
    (list "Q-CSWK-FIXT" 3 "Continuous" "Casework: fixtures (plumbing/service)")
    (list "Q-CSWK-FRMG" 5 "Continuous" "Casework: structural framing")
    (list "Q-CSWK-FULL" 3 "Continuous" "Casework: full-height (cabinets/lockers)")
    (list "Q-CSWK-GLAZ" 4 "Continuous" "Casework: glazing")
    (list "Q-CSWK-GRND" 2 "Continuous" "Casework: ground")
    (list "Q-CSWK-HRDW" 3 "Continuous" "Casework: hardware")
    (list "Q-CSWK-LOWR" 3 "Continuous" "Casework: lower (cabinets)")
    (list "Q-CSWK-PATT" 1 "Continuous" "Casework: texture and hatch patterns")
    (list "Q-CSWK-SHLF" 3 "Continuous" "Casework: wall mounted shelving")
    (list "Q-CSWK-SUBA" 3 "Continuous" "Casework: cabinet sub-assemblies, drawer boxes")
    (list "Q-CSWK-UCTR" 3 "Continuous" "Casework: undercounter (cabinets-for layout)")
    (list "Q-CSWK-UPPR" 3 "Continuous" "Casework: upper (cabinets)")
    (list "Q-CSWK-WKSF" 3 "Continuous" "Casework: work surface")
    (list "Q-ELEV" 2 "Continuous" "Elevation")
    (list "Q-ELEV-EQPM" 4 "Continuous" "Elevation: equipment")
    (list "Q-ELEV-FIXT" 3 "Continuous" "Elevation: fixtures (plumbing/service)")
    (list "Q-ELEV-GLAZ" 4 "Continuous" "Elevation: glazing")
    (list "Q-ELEV-HRDW" 3 "Continuous" "Elevation: hardware")
    (list "Q-ELEV-OVHD" 2 "HIDDEN2" "Elevation: overhead")
    (list "Q-ELEV-PATT" 1 "Continuous" "Elevation: texture and hatch patterns")
    (list "Q-ELEV-STRC" 5 "Continuous" "Elevation: structures (support components)")
    (list "Q-EXHS" 4 "Continuous" "Exhaust system")
    (list "Q-MAJQ" 5 "Continuous" "Major equipment")
    (list "Q-MAJQ-ACCS" 4 "Continuous" "Major equipment: access")
    (list "Q-MAJQ-ENGR" 2 "Continuous" "Major equipment: engineering information")
    (list "Q-MAJQ-FIXD" 5 "Continuous" "Major equipment: fixed")
    (list "Q-MAJQ-MOVE" 4 "Continuous" "Major equipment: movable")
    (list "Q-MAJQ-MVNG" 4 "Continuous" "Major equipment: moving or suspended")
    (list "Q-MAJQ-OVHD" 4 "HIDDEN2" "Major equipment: overhead")
    (list "Q-MAJQ-PATT" 1 "Continuous" "Major equipment: texture and hatch patterns")
    (list "Q-MAJQ-UCTR" 5 "Continuous" "Major equipment: undercounter")
    (list "Q-MINQ" 4 "Continuous" "Minor equipment")
    (list "Q-POWR" 5 "Continuous" "Power")
    (list "Q-SPCL" 4 "Continuous" "Special")
    (list "Q-SPCL-ACCS" 4 "Continuous" "Special: access")
    (list "Q-SPCL-ENGR" 2 "Continuous" "Special: engineering information")
    (list "Q-SPCL-FIXD" 5 "Continuous" "Special: fixed")
    (list "Q-SPCL-MOVE" 4 "Continuous" "Special: movable")
    (list "Q-SPCL-MVNG" 4 "Continuous" "Special: moving or suspended")
    (list "Q-SPCL-OVHD" 4 "HIDDEN2" "Special: overhead")
    (list "Q-SPCL-PATT" 1 "Continuous" "Special: texture and hatch patterns")
    (list "Q-SPCL-UCTR" 4 "Continuous" "Special: undercounter")
  )
)

(setq *layers-F*
  (list
    (list "F-AFFF" 72 "Continuous" "Aqueous film-forming foam system")
    (list "F-AFFF-EQPM" 72 "Continuous" "Aqueous film-forming foam system: equipment")
    (list "F-AFFF-PIPE" 72 "Continuous" "Aqueous film-forming foam system: piping")
    (list "F-CO2S" 71 "Continuous" "CO2 system")
    (list "F-CO2S-EQPM" 71 "Continuous" "CO2 system: equipment")
    (list "F-CO2S-PIPE" 71 "Continuous" "CO2 system: piping")
    (list "F-HALN" 71 "Continuous" "Halon")
    (list "F-HALN-EQPM" 71 "Continuous" "Halon: equipment")
    (list "F-HALN-PIPE" 71 "Continuous" "Halon: piping")
    (list "F-IGAS" 71 "Continuous" "Inert gas")
    (list "F-IGAS-EQPM" 71 "Continuous" "Inert gas: equipment")
    (list "F-IGAS-PIPE" 71 "Continuous" "Inert gas: piping")
    (list "F-PROT" 72 "Continuous" "Fire protection system")
    (list "F-PROT-ALRM" 1 "Continuous" "Fire protection system: alarm")
    (list "F-PROT-EQPM" 72 "Continuous" "Fire protection system: equipment")
    (list "F-PROT-EXTI" 72 "Continuous" "Fire protection system: extinguishers")
    (list "F-PROT-HOSE" 72 "Continuous" "Fire protection system: hoses")
    (list "F-PROT-HYDT" 72 "Continuous" "Fire protection: hydrants and connections")
    (list "F-PROT-RATE" 2 "Continuous" "Fire protection system: ratings")
    (list "F-PROT-RATE-DOOR" 2 "Continuous" "Fire protection system: ratings: doors")
    (list "F-PROT-RATE-WALL" 2 "Continuous" "Fire protection system: ratings: wall")
    (list "F-PROT-SMOK" 71 "Continuous" "Fire protection system: smoke detector/heat sensors")
    (list "F-SPKL" 72 "Continuous" "Sprinkler")
    (list "F-SPKL-CLHD" 72 "Continuous" "Sprinkler: ceiling heads")
    (list "F-SPKL-EQPM" 72 "Continuous" "Sprinkler: equipment")
    (list "F-SPKL-OTHD" 72 "Continuous" "Sprinkler: other heads")
    (list "F-SPKL-PIPE" 72 "Continuous" "Sprinkler: piping")
  )
)

(setq *layers-G*
  (list
    (list "G-ACCS" 2 "Continuous" "Access")
    (list "G-CODE" 2 "Continuous" "Code compliance plan")
    (list "G-EVAC" 1 "Continuous" "Evacuation plan")
    (list "G-FIRE" 1 "Continuous" "Fire protection plan")
    (list "G-PLAN" 2 "Continuous" "Key plan (floor plan)")
    (list "G-SITE" 2 "Continuous" "Key plan (site features)")
  )
)

(setq *layers-B*
  (list
    (list "B-BORE" 11 "Continuous" "Borings")
    (list "B-BORE-FDTA" 11 "Continuous" "Borings: field data")
    (list "B-BORE-HOLE" 11 "Continuous" "Borings: holes (perc)")
    (list "B-BORE-LDTA" 11 "Continuous" "Borings: laboratory data")
    (list "B-DETL-CONC" 12 "Continuous" "Detail: concrete")
    (list "B-DETL-ERTH" 11 "Continuous" "Detail: earth")
    (list "B-DETL-FDTA" 11 "Continuous" "Detail: field data")
    (list "B-DETL-FILL" 11 "Continuous" "Detail: fill and cover material")
    (list "B-DETL-GENF" 11 "Continuous" "Detail: general features")
    (list "B-DETL-GNDW" 11 "Continuous" "Detail: ground water")
    (list "B-DETL-LDTA" 11 "Continuous" "Detail: laboratory data")
    (list "B-DETL-PVMT" 12 "Continuous" "Detail: pavement")
    (list "B-DETL-SPCL" 11 "Continuous" "Detail: special")
    (list "B-DETL-STRM" 11 "Continuous" "Detail: storm sewer")
    (list "B-DETL-SUBS" 11 "Continuous" "Detail: sub-surface areas")
    (list "B-DETL-SURF" 11 "Continuous" "Detail: surface areas")
  )
)

(setq *layers-H*
  (list
    (list "H-PLAN" 1 "Continuous" "Key plan (floor plan)")
    (list "H-SITE" 1 "Continuous" "Key plan (site features)")
  )
)

(setq *layers-I*
  (list
    (list "I-AREA" 2 "Continuous" "Area")
    (list "I-AREA-OCCP" 2 "Continuous" "Area: occupant or employee names")
    (list "I-CLNG" 30 "Continuous" "Ceiling")
    (list "I-CLNG-ACCS" 30 "Continuous" "Ceiling: access")
    (list "I-CLNG-OPNG" 30 "Continuous" "Ceiling: openings")
    (list "I-CLNG-SUSP" 30 "Continuous" "Ceiling: suspended elements")
    (list "I-CLNG-TEES" 30 "Continuous" "Ceiling: main tees")
    (list "I-COLS" 7 "Continuous" "Columns")
    (list "I-CRPT" 1 "Continuous" "Carpet/carpet tile")
    (list "I-CSWK" 3 "Continuous" "Casework")
    (list "I-DOOR" 3 "Continuous" "Doors")
    (list "I-DOOR-FULL" 3 "Continuous" "Doors: full-height")
    (list "I-DOOR-PRHT" 3 "Continuous" "Doors: partial-height")
    (list "I-EQPM" 4 "Continuous" "Equipment")
    (list "I-EQPM-ACCS" 4 "Continuous" "Equipment: access")
    (list "I-EQPM-FIXD" 4 "Continuous" "Equipment: fixed")
    (list "I-EQPM-OVHD" 4 "HIDDEN2" "Equipment: overhead")
    (list "I-EQPM-STOR" 4 "Continuous" "Equipment: storage")
    (list "I-FLOR" 2 "Continuous" "Floor")
    (list "I-FLOR-EVTR" 3 "Continuous" "Floor: elevator cars and equipment")
    (list "I-FLOR-FIXT" 3 "Continuous" "Floor: fixtures (plumbing)")
    (list "I-FLOR-HRAL" 3 "Continuous" "Floor: handrails/guard rails")
    (list "I-FLOR-LEVL" 2 "Continuous" "Floor: level changes")
    (list "I-FLOR-OTLN" 5 "Continuous" "Floor: outline")
    (list "I-FLOR-OVHD" 2 "HIDDEN2" "Floor: overhead")
    (list "I-FLOR-RAIS" 3 "Continuous" "Floor: raised")
    (list "I-FLOR-RISR" 3 "Continuous" "Floor: risers")
    (list "I-FLOR-SIGN" 2 "Continuous" "Floor: signage")
    (list "I-FLOR-SPCL" 3 "Continuous" "Floor: architectural specialties")
    (list "I-FLOR-STRS" 3 "Continuous" "Floor: stair treads (escalators, ladders)")
    (list "I-FLOR-TPTN" 3 "Continuous" "Floor: toilet partitions")
    (list "I-FLOR-WDWK" 3 "Continuous" "Floor: architectural woodwork")
    (list "I-FNSH" 2 "Continuous" "Finishes")
    (list "I-FURN" 8 "Continuous" "Furnishings")
    (list "I-FURN-FILE" 8 "Continuous" "Furnishings: file cabinets")
    (list "I-FURN-FREE" 8 "Continuous" "Furnishings: freestanding")
    (list "I-FURN-PLNT" 8 "Continuous" "Furnishings: plants")
    (list "I-FURN-PNLS" 8 "Continuous" "Furnishings: system panels")
    (list "I-FURN-SEAT" 8 "Continuous" "Furnishings: seating")
    (list "I-FURN-STOR" 8 "Continuous" "Furnishings: storage (component system)")
    (list "I-FURN-WKSF" 8 "Continuous" "Furnishings: work surface (component system)")
    (list "I-GLAZ" 4 "Continuous" "Glazing")
    (list "I-GLAZ-FULL" 4 "Continuous" "Glazing: full-height")
    (list "I-GLAZ-PRHT" 4 "Continuous" "Glazing: partial-height")
    (list "I-GLAZ-SILL" 3 "Continuous" "Glazing: window sills")
    (list "I-HVAC" 4 "Continuous" "HVAC systems")
    (list "I-HVAC-RDFF" 4 "Continuous" "HVAC systems: return air diffusers")
    (list "I-HVAC-SDFF" 4 "Continuous" "HVAC systems: supply diffusers")
    (list "I-MILL" 3 "Continuous" "Millwork")
    (list "I-PRTN" 5 "Continuous" "Partitions")
    (list "I-PRTN-FIRE" 5 "Continuous" "Partitions: fire protection")
    (list "I-PRTN-FULL" 5 "Continuous" "Partitions: full-height")
    (list "I-PRTN-HEAD" 3 "Continuous" "Partitions: door and window headers")
    (list "I-PRTN-JAMB" 3 "Continuous" "Partitions: door and window jambs")
    (list "I-PRTN-MOVE" 3 "Continuous" "Partitions: moveable")
    (list "I-PRTN-PRHT" 3 "Continuous" "Partitions: partial-height")
    (list "I-TILE" 1 "Continuous" "Tile")
  )
)

(setq *layers-L*
  (list
    (list "L-FENC" 42 "Continuous" "Fences")
    (list "L-FENC-LINK" 42 "Continuous" "Fences: chain link")
    (list "L-FENC-LINK-04FT" 41 "Continuous" "Fences: chain link: four feet high")
    (list "L-FENC-LINK-06FT" 42 "Continuous" "Fences: chain link: six feet high")
    (list "L-FENC-PRVC" 42 "Continuous" "Fences: privacy")
    (list "L-FENC-WOOD" 42 "Continuous" "Fences: wood")
    (list "L-IRRG" 41 "Continuous" "Irrigation")
    (list "L-IRRG-COVR" 41 "Continuous" "Irrigation: coverage")
    (list "L-IRRG-DRIP" 41 "Continuous" "Irrigation: drip irrigation tubing")
    (list "L-IRRG-EQPM" 42 "Continuous" "Irrigation: equipment (pumps, valves, and controllers)")
    (list "L-IRRG-LTRL" 41 "Continuous" "Irrigation: lateral pipe")
    (list "L-IRRG-MAIN" 42 "Continuous" "Irrigation: mainline")
    (list "L-IRRG-PIPE" 41 "Continuous" "Irrigation: piping")
    (list "L-IRRG-SLVE" 41 "Continuous" "Irrigation: pipe sleeve")
    (list "L-IRRG-SPKL" 41 "Continuous" "Irrigation: sprinklers (rotors, heads)")
    (list "L-IRRG-VALV" 42 "Continuous" "Irrigation: valves")
    (list "L-PLNT" 42 "Continuous" "Plant and landscape material")
    (list "L-PLNT-BEDS" 41 "Continuous" "Plant and landscape material: perennial and annual beds")
    (list "L-PLNT-BUSH" 42 "Continuous" "Plant and landscape material: bushes and shrubs")
    (list "L-PLNT-CONI" 43 "Continuous" "Plant and landscape material: coniferous trees")
    (list "L-PLNT-CTNR" 42 "Continuous" "Plant and landscape material: container or planter")
    (list "L-PLNT-EDGR" 41 "Continuous" "Plant and landscape material: planting bed edger")
    (list "L-PLNT-EVGR" 43 "Continuous" "Plant and landscape material: evergreen trees - broadleaf")
    (list "L-PLNT-GCVR" 41 "Continuous" "Plant and landscape material: ground cover")
    (list "L-PLNT-MLCH" 41 "Continuous" "Plant and landscape material: mulches")
    (list "L-PLNT-PALM" 43 "Continuous" "Plant and landscape material: palm trees")
    (list "L-PLNT-PLNT" 42 "Continuous" "Plant and landscape material: plants")
    (list "L-PLNT-SEED" 41 "Continuous" "Plant and landscape material: seeding areas")
    (list "L-PLNT-SHAD" 41 "Continuous" "Plant and landscape material: shadow area")
    (list "L-PLNT-TREE" 43 "Continuous" "Plant and landscape material: trees")
    (list "L-PLNT-TURF" 41 "Continuous" "Plant and landscape material: lawn areas")
    (list "L-PLNT-VINE" 41 "Continuous" "Plant and landscape material: vines")
    (list "L-PVMT" 12 "Continuous" "Pavement")
    (list "L-PVMT-ASPH" 12 "Continuous" "Pavement: asphalt")
    (list "L-PVMT-BRCK" 12 "Continuous" "Pavement: brick")
    (list "L-PVMT-CONC" 12 "Continuous" "Pavement: concrete")
    (list "L-PVMT-CONC-AGGR" 12 "Continuous" "Pavement: concrete: exposed aggregate")
    (list "L-PVMT-GRVL" 12 "Continuous" "Pavement: gravel")
    (list "L-PVMT-JNTC" 11 "Continuous" "Pavement: control joint")
    (list "L-PVMT-JNTE" 11 "Continuous" "Pavement: expansion joint")
    (list "L-PVMT-PAVR" 12 "Continuous" "Pavement: unit pavers")
    (list "L-PVMT-RAMP" 12 "Continuous" "Pavement: accessible ramp")
    (list "L-PVMT-STRS" 12 "Continuous" "Pavement: stair treads")
    (list "L-SITE" 42 "Continuous" "Site features")
    (list "L-SITE-BRDG" 43 "Continuous" "Site features: bridge (pedestrian)")
    (list "L-SITE-CURB" 43 "Continuous" "Site features: curb")
    (list "L-SITE-CURB-BACK" 42 "Continuous" "Site features: curb: back")
    (list "L-SITE-CURB-FACE" 43 "Continuous" "Site features: curb: face")
    (list "L-SITE-DECK" 42 "Continuous" "Site features: deck (wood, typ.)")
    (list "L-SITE-FURN" 42 "Continuous" "Site features: furnishings")
    (list "L-SITE-PLAY" 42 "Continuous" "Site features: play structures")
    (list "L-SITE-PLAY-EQPM" 42 "Continuous" "Site features: play structures: equipment")
    (list "L-SITE-PLAY-ZONE" 41 "Continuous" "Site features: play structures: zoning")
    (list "L-SITE-POOL" 43 "Continuous" "Site features: pools and spas")
    (list "L-SITE-POOL-BACK" 42 "Continuous" "Site features: pools and spas: back of pool wall")
    (list "L-SITE-POOL-FACE" 43 "Continuous" "Site features: pools and spas: face of pool wall")
    (list "L-SITE-PRKG" 12 "Continuous" "Site features: parking")
    (list "L-SITE-PRKG-STRP" 11 "Continuous" "Site features: parking: striping")
    (list "L-SITE-ROAD" 13 "Continuous" "Site features: edge of roadway line")
    (list "L-SITE-ROCK" 42 "Continuous" "Site features: large rocks and rock outcroppings")
    (list "L-SITE-RRAP" 42 "Continuous" "Site features: riprap")
    (list "L-SITE-RTWL" 43 "Continuous" "Site features: retaining wall")
    (list "L-SITE-SPRT" 42 "Continuous" "Site features: sports fields")
    (list "L-SITE-SPRT-EQPM" 42 "Continuous" "Site features: sports fields: equipment")
    (list "L-SITE-SPRT-PERI" 43 "Continuous" "Site features: sports fields: perimeter")
    (list "L-SITE-STEP" 42 "Continuous" "Site features: steps")
    (list "L-SITE-SWLK" 42 "Continuous" "Site features: sidewalks and steps")
    (list "L-SITE-TRAL" 42 "Continuous" "Site features: trail or path")
    (list "L-SITE-TRAL-ASPH" 41 "Continuous" "Site features: trail or path: asphalt")
    (list "L-SITE-TRAL-CONC" 41 "Continuous" "Site features: trail or path: concrete")
    (list "L-SITE-TRAL-GRVL" 41 "Continuous" "Site features: trail or path: gravel")
    (list "L-SITE-WALL" 43 "Continuous" "Site features: walls")
    (list "L-SITE-WEIR" 43 "Continuous" "Site features: pool weir")
    (list "L-TOPO" 41 "Continuous" "Topographic feature")
    (list "L-TOPO-LIMI" 41 "Continuous" "Topographic feature: limit of earthwork")
    (list "L-TOPO-SPOT" 2 "Continuous" "Topographic feature: spot elevations")
  )
)

(setq *layers-M*
  (list
    (list "M-BRIN" 4 "Continuous" "Brine systems")
    (list "M-BRIN-EQPM" 4 "Continuous" "Brine systems: equipment")
    (list "M-BRIN-PIPE" 4 "Continuous" "Brine systems: piping")
    (list "M-CHIM" 5 "Continuous" "Chimneys and stacks")
    (list "M-CMPA" 4 "Continuous" "Compressed/processed air systems")
    (list "M-CMPA-EQPM" 4 "Continuous" "Compressed/processed air systems: equipment")
    (list "M-CMPA-PEQP" 4 "Continuous" "Compressed/processed air systems: process equipment")
    (list "M-CMPA-PIPE" 4 "Continuous" "Compressed/processed air systems: piping")
    (list "M-CMPA-PPIP" 4 "Continuous" "Compressed/processed air systems: process piping")
    (list "M-CNDW" 4 "Continuous" "Condenser water systems")
    (list "M-CNDW-EQPM" 4 "Continuous" "Condenser water systems: equipment")
    (list "M-CNDW-PIPE" 4 "Continuous" "Condenser water systems: piping")
    (list "M-CNDW-RETN" 4 "Continuous" "Condenser water systems: return")
    (list "M-CNDW-RETN-PIPE" 4 "Continuous" "Condenser water systems: return: piping")
    (list "M-CNDW-RETN-SKCH" 2 "Continuous" "Condenser water systems: return: sketch")
    (list "M-CNDW-SPLY" 4 "Continuous" "Condenser water systems: supply")
    (list "M-CNDW-SPLY-PIPE" 4 "Continuous" "Condenser water systems: supply: piping")
    (list "M-CNDW-SPLY-SKCH" 2 "Continuous" "Condenser water systems: supply: sketch")
    (list "M-CONT" 4 "Continuous" "Controls and instrumentation")
    (list "M-CONT-THER" 4 "Continuous" "Controls and instrumentation: thermostats")
    (list "M-CONT-WIRE" 4 "Continuous" "Controls and instrumentation: wiring (low voltage)")
    (list "M-CWTR" 4 "Continuous" "Chilled water systems")
    (list "M-CWTR-CNDS" 4 "Continuous" "Chilled water systems: condensate piping")
    (list "M-CWTR-EQPM" 4 "Continuous" "Chilled water systems: equipment")
    (list "M-CWTR-PIPE" 4 "Continuous" "Chilled water systems: piping")
    (list "M-CWTR-RETN" 4 "Continuous" "Chilled water systems: return")
    (list "M-CWTR-RETN-PIPE" 4 "Continuous" "Chilled water systems: return: piping")
    (list "M-CWTR-RETN-SKCH" 2 "Continuous" "Chilled water systems: return: sketch")
    (list "M-CWTR-SPLY" 4 "Continuous" "Chilled water systems: supply")
    (list "M-CWTR-SPLY-PIPE" 4 "Continuous" "Chilled water systems: supply: piping")
    (list "M-CWTR-SPLY-SKCH" 2 "Continuous" "Chilled water systems: supply: sketch")
    (list "M-DOMW" 4 "Continuous" "Domestic water systems")
    (list "M-DOMW-MKUP" 4 "Continuous" "Domestic water systems: make-up water")
    (list "M-DUAL" 4 "Continuous" "Dual temperature systems")
    (list "M-DUAL-RETN" 4 "Continuous" "Dual temperature systems: return")
    (list "M-DUAL-RETN-PIPE" 4 "Continuous" "Dual temperature systems: return: piping")
    (list "M-DUAL-RETN-SKCH" 2 "Continuous" "Dual temperature systems: return: sketch")
    (list "M-DUAL-SPLY" 4 "Continuous" "Dual temperature systems: supply")
    (list "M-DUAL-SPLY-PIPE" 4 "Continuous" "Dual temperature systems: supply: piping")
    (list "M-DUAL-SPLY-SKCH" 2 "Continuous" "Dual temperature systems: supply: sketch")
    (list "M-DUST" 4 "Continuous" "Dust and fume collection systems")
    (list "M-DUST-DUCT" 4 "Continuous" "Dust and fume collection systems: ductwork")
    (list "M-DUST-DUCT-CNTR" 2 "CENTER2" "Dust and fume collection systems: ductwork: center")
    (list "M-DUST-EQPM" 4 "Continuous" "Dust and fume collection systems: equipment")
    (list "M-ELHT" 5 "Continuous" "Electric heat")
    (list "M-ELHT-EQPM" 5 "Continuous" "Electric heat: equipment")
    (list "M-ENER" 4 "Continuous" "Energy management systems")
    (list "M-ENER-EQPM" 4 "Continuous" "Energy management systems: equipment")
    (list "M-ENER-WIRE" 4 "Continuous" "Energy management systems: wiring")
    (list "M-EXHS" 4 "Continuous" "Exhaust system")
    (list "M-EXHS-CDFF" 4 "Continuous" "Exhaust system: ceiling diffusers")
    (list "M-EXHS-DUCT" 4 "Continuous" "Exhaust system: ductwork")
    (list "M-EXHS-DUCT-CNTR" 2 "CENTER2" "Exhaust system: ductwork: center")
    (list "M-EXHS-EQPM" 4 "Continuous" "Exhaust system: equipment")
    (list "M-EXHS-RFEQ" 4 "Continuous" "Exhaust system: rooftop equipment")
    (list "M-FLOR" 2 "Continuous" "Floor")
    (list "M-FLOR-PENE" 2 "Continuous" "Floor: penetrations")
    (list "M-FUEL" 4 "Continuous" "Fuel systems")
    (list "M-FUEL-EQPM" 4 "Continuous" "Fuel systems: equipment")
    (list "M-FUEL-GGEP" 4 "Continuous" "Fuel systems: gas general piping")
    (list "M-FUEL-GGEP-HPIP" 4 "Continuous" "Fuel systems: gas general piping: high pressure piping")
    (list "M-FUEL-GGEP-LPIP" 4 "Continuous" "Fuel systems: gas general piping: low-pressure piping")
    (list "M-FUEL-GGEP-LQPG" 4 "Continuous" "Fuel systems: gas general piping: liquid petroleum gas")
    (list "M-FUEL-GGEP-MPIP" 4 "Continuous" "Fuel systems: gas general piping: medium-pressure piping")
    (list "M-FUEL-GPRP" 4 "Continuous" "Fuel systems: gas process piping")
    (list "M-FUEL-OPRP" 4 "Continuous" "Fuel systems: oil process piping")
    (list "M-FUEL-OGEP" 4 "Continuous" "Fuel systems: oil general piping")
    (list "M-FUEL-OGEP-DISC" 4 "Continuous" "Fuel systems: oil general piping: discharge")
    (list "M-FUEL-OGEP-FLLW" 4 "Continuous" "Fuel systems: oil general piping: flow")
    (list "M-FUEL-OGEP-GAGE" 4 "Continuous" "Fuel systems: oil general piping: gauge")
    (list "M-FUEL-OGEP-RETN" 4 "Continuous" "Fuel systems: oil general piping: return")
    (list "M-FUEL-OGEP-SPLY" 4 "Continuous" "Fuel systems: oil general piping: supply")
    (list "M-FUEL-OGEP-VENT" 4 "Continuous" "Fuel systems: oil general piping: vents")
    (list "M-FUME" 4 "Continuous" "Fume hood")
    (list "M-FUME-DUCT" 4 "Continuous" "Fume hood: ductwork")
    (list "M-FUME-EQPM" 4 "Continuous" "Fume hood: equipment")
    (list "M-GLYC" 4 "Continuous" "Glycol systems")
    (list "M-GLYC-RETN" 4 "Continuous" "Glycol systems: return")
    (list "M-GLYC-RETN-PIPE" 4 "Continuous" "Glycol systems: return: piping")
    (list "M-GLYC-RETN-SKCH" 2 "Continuous" "Glycol systems: return: sketch")
    (list "M-GLYC-SPLY" 4 "Continuous" "Glycol systems: supply")
    (list "M-GLYC-SPLY-PIPE" 4 "Continuous" "Glycol systems: supply: piping")
    (list "M-GLYC-SPLY-SKCH" 2 "Continuous" "Glycol systems: supply: sketch")
    (list "M-HVAC" 5 "Continuous" "HVAC systems")
    (list "M-HVAC-BOXD" 4 "Continuous" "HVAC systems: mixing box, dual duct")
    (list "M-HVAC-BOXS" 4 "Continuous" "HVAC systems: mixing box, single duct")
    (list "M-HVAC-CDFF" 4 "Continuous" "HVAC systems: ceiling diffusers")
    (list "M-HVAC-CLDA" 5 "Continuous" "HVAC systems: cold air")
    (list "M-HVAC-CLDA-DUCT" 5 "Continuous" "HVAC systems: cold air: ductwork")
    (list "M-HVAC-CLDA-EQPM" 4 "Continuous" "HVAC systems: cold air: equipment")
    (list "M-HVAC-CLDA-RSCH" 2 "Continuous" "HVAC systems: cold air: sketch line round or oval duct")
    (list "M-HVAC-CLDA-SECT" 2 "Continuous" "HVAC systems: cold air: section")
    (list "M-HVAC-CLDA-SIZE" 2 "Continuous" "HVAC systems: cold air: ductwork size")
    (list "M-HVAC-CLDA-SSCH" 2 "Continuous" "HVAC systems: cold air: sketch line rectangular duct")
    (list "M-HVAC-DMPR" 4 "Continuous" "HVAC systems: fire, smoke, volume damper")
    (list "M-HVAC-DOOR" 4 "Continuous" "HVAC systems: equipment doors")
    (list "M-HVAC-EFAN" 4 "Continuous" "HVAC systems: equipment with electric fans")
    (list "M-HVAC-EPDU" 4 "Continuous" "HVAC systems: equipment with piping, ductwork and electricity")
    (list "M-HVAC-EPIP" 4 "Continuous" "HVAC systems: equipment with piping and electricity")
    (list "M-HVAC-EQPM" 5 "Continuous" "HVAC systems: equipment")
    (list "M-HVAC-EXHS" 4 "Continuous" "HVAC systems: exhaust air")
    (list "M-HVAC-EXHS-DUCT" 4 "Continuous" "HVAC systems: exhaust air: ductwork")
    (list "M-HVAC-EXHS-EQPM" 4 "Continuous" "HVAC systems: exhaust air: equipment")
    (list "M-HVAC-EXHS-GRIL" 4 "Continuous" "HVAC systems: exhaust air: grilles")
    (list "M-HVAC-EXHS-RSCH" 2 "Continuous" "HVAC systems: exhaust air: sketch line round or oval duct")
    (list "M-HVAC-EXHS-SECT" 2 "Continuous" "HVAC systems: exhaust air: section")
    (list "M-HVAC-EXHS-SIZE" 2 "Continuous" "HVAC systems: exhaust air: ductwork size")
    (list "M-HVAC-EXHS-SSCH" 2 "Continuous" "HVAC systems: exhaust air: sketch line rectangular duct")
    (list "M-HVAC-HOTA" 5 "Continuous" "HVAC systems: hot air")
    (list "M-HVAC-HOTA-DUCT" 5 "Continuous" "HVAC systems: hot air: ductwork")
    (list "M-HVAC-HOTA-EQPM" 4 "Continuous" "HVAC systems: hot air: equipment")
    (list "M-HVAC-HOTA-RSCH" 2 "Continuous" "HVAC systems: hot air: sketch line round or oval duct")
    (list "M-HVAC-HOTA-SECT" 2 "Continuous" "HVAC systems: hot air: section")
    (list "M-HVAC-HOTA-SIZE" 2 "Continuous" "HVAC systems: hot air: ductwork size")
    (list "M-HVAC-HOTA-SSCH" 2 "Continuous" "HVAC systems: hot air: sketch line rectangular duct")
    (list "M-HVAC-ODFF" 4 "Continuous" "HVAC systems: other diffusers")
    (list "M-HVAC-PIPE" 4 "Continuous" "HVAC systems: piping")
    (list "M-HVAC-RDFF" 4 "Continuous" "HVAC systems: return air diffusers")
    (list "M-HVAC-RETN" 4 "Continuous" "HVAC systems: return")
    (list "M-HVAC-RETN-CNTR" 2 "CENTER2" "HVAC systems: return: center")
    (list "M-HVAC-RETN-EQPM" 4 "Continuous" "HVAC systems: return: equipment")
    (list "M-HVAC-RETN-RSCH" 2 "Continuous" "HVAC systems: return: sketch line round or oval duct")
    (list "M-HVAC-RETN-SECT" 2 "Continuous" "HVAC systems: return: section")
    (list "M-HVAC-RETN-SIZE" 2 "Continuous" "HVAC systems: return: ductwork size")
    (list "M-HVAC-RETN-SSCH" 2 "Continuous" "HVAC systems: return: sketch line rectangular duct")
    (list "M-HVAC-SDFF" 4 "Continuous" "HVAC systems: supply diffusers")
    (list "M-HVAC-SPLY" 5 "Continuous" "HVAC systems: supply")
    (list "M-HVAC-SPLY-CNTR" 2 "CENTER2" "HVAC systems: supply: center")
    (list "M-HVAC-SPLY-EQPM" 4 "Continuous" "HVAC systems: supply: equipment")
    (list "M-HVAC-SPLY-RSCH" 2 "Continuous" "HVAC systems: supply: sketch line round or oval duct")
    (list "M-HVAC-SPLY-SECT" 2 "Continuous" "HVAC systems: supply: section")
    (list "M-HVAC-SPLY-SIZE" 2 "Continuous" "HVAC systems: supply: ductwork size")
    (list "M-HVAC-SPLY-SSCH" 2 "Continuous" "HVAC systems: supply: sketch line rectangular duct")
    (list "M-HWTR" 4 "Continuous" "Hot water heating system")
    (list "M-HWTR-EQPM" 4 "Continuous" "Hot water heating system: equipment")
    (list "M-HWTR-PIPE" 4 "Continuous" "Hot water heating system: piping")
    (list "M-HWTR-RETN" 4 "Continuous" "Hot water heating system: return")
    (list "M-HWTR-RETN-PIPE" 4 "Continuous" "Hot water heating system: return: piping")
    (list "M-HWTR-RETN-SKCH" 2 "Continuous" "Hot water heating system: return: sketch")
    (list "M-HWTR-SPLY" 4 "Continuous" "Hot water heating system: supply")
    (list "M-HWTR-SPLY-PIPE" 4 "Continuous" "Hot water heating system: supply: piping")
    (list "M-HWTR-SPLY-SKCH" 2 "Continuous" "Hot water heating system: supply: sketch")
    (list "M-LGAS" 4 "Continuous" "Laboratory gas systems")
    (list "M-LGAS-EQPM" 4 "Continuous" "Laboratory gas systems: equipment")
    (list "M-LGAS-PIPE" 4 "Continuous" "Laboratory gas systems: piping")
    (list "M-MACH" 5 "Continuous" "Machine shop")
    (list "M-MDGS" 4 "Continuous" "Medical gas systems")
    (list "M-MDGS-CAIR" 4 "Continuous" "Medical gas systems: compressed air")
    (list "M-MDGS-EQPM" 4 "Continuous" "Medical gas systems: equipment")
    (list "M-MDGS-NITG" 4 "Continuous" "Medical gas systems: nitrogen")
    (list "M-MDGS-NOXG" 4 "Continuous" "Medical gas systems: nitrous oxide")
    (list "M-MDGS-OXYG" 4 "Continuous" "Medical gas systems: pure O2")
    (list "M-MDGS-PIPE" 4 "Continuous" "Medical gas systems: piping")
    (list "M-MDGS-SAIR" 4 "Continuous" "Medical gas systems: scavenge air")
    (list "M-MDGS-VACU" 4 "Continuous" "Medical gas systems: vacuum")
    (list "M-MKUP" 4 "Continuous" "Make-up air systems")
    (list "M-MKUP-CDFF" 4 "Continuous" "Make-up air systems: ceiling diffusers")
    (list "M-MKUP-DUCT" 4 "Continuous" "Make-up air systems: ductwork")
    (list "M-MKUP-EQPM" 4 "Continuous" "Make-up air systems: equipment")
    (list "M-MPIP" 4 "Continuous" "Miscellaneous piping systems")
    (list "M-MPIP-PIPE" 4 "Continuous" "Miscellaneous piping systems: piping")
    (list "M-NGAS" 4 "Continuous" "Natural gas systems")
    (list "M-NGAS-EQPM" 4 "Continuous" "Natural gas systems: equipment")
    (list "M-NGAS-PIPE" 4 "Continuous" "Natural gas systems: piping")
    (list "M-PROC" 4 "Continuous" "Process systems")
    (list "M-PROC-EQPM" 4 "Continuous" "Process systems: equipment")
    (list "M-PROC-PIPE" 4 "Continuous" "Process systems: piping")
    (list "M-RAIR" 4 "Continuous" "Relief air systems")
    (list "M-RCOV" 4 "Continuous" "Energy recovery systems")
    (list "M-RCOV-EQPM" 4 "Continuous" "Energy recovery systems: equipment")
    (list "M-RCOV-PIPE" 4 "Continuous" "Energy recovery systems: piping")
    (list "M-REFG" 4 "Continuous" "Refrigeration systems")
    (list "M-REFG-DISC" 4 "Continuous" "Refrigeration systems: discharge")
    (list "M-REFG-EQPM" 4 "Continuous" "Refrigeration systems: equipment")
    (list "M-REFG-PIPE" 4 "Continuous" "Refrigeration systems: piping")
    (list "M-REFG-RETN" 4 "Continuous" "Refrigeration systems: return")
    (list "M-REFG-SPLY" 4 "Continuous" "Refrigeration systems: supply")
    (list "M-ROOF" 5 "Continuous" "Roof")
    (list "M-ROOF-PENE" 3 "Continuous" "Roof: penetrations")
    (list "M-SMOK" 4 "Continuous" "Smoke extraction systems")
    (list "M-SMOK-CDFF" 4 "Continuous" "Smoke extraction systems: ceiling diffusers")
    (list "M-SMOK-DUCT" 4 "Continuous" "Smoke extraction systems: ductwork")
    (list "M-SMOK-EQPM" 4 "Continuous" "Smoke extraction systems: equipment")
    (list "M-SPCL" 4 "Continuous" "Special systems")
    (list "M-SPCL-EQPM" 4 "Continuous" "Special systems: equipment")
    (list "M-SPCL-PIPE" 4 "Continuous" "Special systems: piping")
    (list "M-STEM" 4 "Continuous" "Steam system")
    (list "M-STEM-BLBD" 4 "Continuous" "Steam system: boiler blow down piping")
    (list "M-STEM-BLBD-PIPE" 4 "Continuous" "Steam system: boiler blow down piping: piping")
    (list "M-STEM-CNDS" 4 "Continuous" "Steam system: condensate piping")
    (list "M-STEM-CNDS-SKCH" 2 "Continuous" "Steam system: condensate piping: sketch")
    (list "M-STEM-EQPM" 4 "Continuous" "Steam system: equipment")
    (list "M-STEM-HPIP" 4 "Continuous" "Steam system: high-pressure piping")
    (list "M-STEM-HPIP-SKCH" 2 "Continuous" "Steam system: high-pressure piping: sketch")
    (list "M-STEM-LPIP" 4 "Continuous" "Steam system: low-pressure piping")
    (list "M-STEM-LPIP-SKCH" 2 "Continuous" "Steam system: low-pressure piping: sketch")
    (list "M-STEM-MPIP" 4 "Continuous" "Steam system: medium-pressure piping")
    (list "M-STEM-MPIP-SKCH" 2 "Continuous" "Steam system: medium-pressure piping: sketch")
    (list "M-TEST" 4 "Continuous" "Test equipment")
    (list "M-WALL" 5 "Continuous" "Wall")
    (list "M-WALL-PENE" 3 "Continuous" "Wall: penetrations")
  )
)

(setq *layers-P*
  (list
    (list "P-ACID" 4 "Continuous" "Acid waste systems")
    (list "P-ACID-EQPM" 4 "Continuous" "Acid waste systems: equipment")
    (list "P-ACID-PIPE" 4 "Continuous" "Acid waste systems: piping")
    (list "P-ACID-VENT" 4 "Continuous" "Acid waste systems: vents")
    (list "P-DOMW" 5 "Continuous" "Domestic water systems")
    (list "P-DOMW-CPIP" 5 "Continuous" "Domestic water systems: cold water piping")
    (list "P-DOMW-EQPM" 5 "Continuous" "Domestic water systems: equipment")
    (list "P-DOMW-HPIP" 5 "DASHED2" "Domestic water systems: hot water piping")
    (list "P-DOMW-RISR" 5 "Continuous" "Domestic water systems: risers")
    (list "P-DOMW-RPIP" 5 "DASHED2" "Domestic water systems: recirculation piping")
    (list "P-FLOR" 2 "Continuous" "Floor")
    (list "P-FLOR-PENE" 2 "Continuous" "Floor: penetrations")
    (list "P-MDGS" 4 "Continuous" "Medical gas systems")
    (list "P-MDGS-CAIR" 4 "Continuous" "Medical gas systems: compressed air")
    (list "P-MDGS-EQPM" 4 "Continuous" "Medical gas systems: equipment")
    (list "P-MDGS-NITG" 4 "Continuous" "Medical gas systems: nitrogen")
    (list "P-MDGS-NOXG" 4 "Continuous" "Medical gas systems: nitrous oxide")
    (list "P-MDGS-OXYG" 4 "Continuous" "Medical gas systems: pure O2")
    (list "P-MDGS-PIPE" 4 "Continuous" "Medical gas systems: piping")
    (list "P-MDGS-SAIR" 4 "Continuous" "Medical gas systems: scavenge air")
    (list "P-MDGS-VACU" 4 "Continuous" "Medical gas systems: vacuum")
    (list "P-ROOF" 5 "Continuous" "Roof")
    (list "P-ROOF-PENE" 3 "Continuous" "Roof: penetrations")
    (list "P-SSWR" 4 "Continuous" "Sanitary sewer")
    (list "P-SSWR-EQPM" 4 "Continuous" "Sanitary sewer: equipment")
    (list "P-SSWR-FIXT" 3 "Continuous" "Sanitary sewer: fixtures")
    (list "P-SSWR-FLDR" 4 "Continuous" "Sanitary sewer: floor drains")
    (list "P-SSWR-PIPE" 4 "Continuous" "Sanitary sewer: piping")
    (list "P-SSWR-RISR" 4 "Continuous" "Sanitary sewer: risers")
    (list "P-SSWR-VENT" 4 "Continuous" "Sanitary sewer: vents")
    (list "P-STRM" 4 "Continuous" "Storm sewer")
    (list "P-STRM-PIPE" 4 "Continuous" "Storm sewer: piping")
    (list "P-STRM-RFDR" 4 "Continuous" "Storm sewer: roof drains")
    (list "P-STRM-RISR" 4 "Continuous" "Storm sewer: risers")
    (list "P-WALL" 5 "Continuous" "Wall")
    (list "P-WALL-PENE" 3 "Continuous" "Wall: penetrations")
  )
)

(setq *layers-R*
  (list
    (list "R-INGR" 31 "Continuous" "Ingrants")
    (list "R-INGR-ESMT" 31 "DASHED2" "Ingrants: easement")
    (list "R-INGR-LEAS" 31 "Continuous" "Ingrants: lease")
    (list "R-INGR-LICN" 31 "Continuous" "Ingrants: license")
    (list "R-INGR-PMIT" 31 "Continuous" "Ingrants: permit")
    (list "R-INGR-RSRV" 31 "Continuous" "Ingrants: reservation")
    (list "R-LAND" 31 "Continuous" "Land")
    (list "R-LAND-ALOC" 31 "Continuous" "Land: allocation")
    (list "R-LAND-CLAS" 31 "Continuous" "Land: classification")
    (list "R-OTGR" 31 "Continuous" "Outgrants")
    (list "R-OTGR-LEAS" 31 "Continuous" "Outgrants: lease")
    (list "R-OTGR-LICN" 31 "Continuous" "Outgrants: license")
    (list "R-OTGR-PMIT" 31 "Continuous" "Outgrants: permit")
    (list "R-OTGR-RSRV" 31 "Continuous" "Outgrants: reservation")
    (list "R-PROP" 6 "Continuous" "Property")
    (list "R-PROP-PRCL" 6 "Continuous" "Property: parcels")
    (list "R-PROP-TAKE" 6 "Continuous" "Property: taking lines")
    (list "R-PROP-TAKE-ELEV" 2 "Continuous" "Property: taking lines: elevations")
    (list "R-PROP-TRAC" 6 "Continuous" "Property: tract lines")
    (list "R-PROP-TRAC-DFEE" 2 "DASHED2" "Property: tract lines: disposed fee")
    (list "R-PROP-TRAC-FEE" 6 "Continuous" "Property: tract lines: fee")
    (list "R-PROP-TRAC-LFEE" 2 "DASHED2" "Property: tract lines: disposed less than fee")
    (list "R-PROP-TRAC-NFEE" 2 "DASHED2" "Property: tract lines: non-fee")
  )
)

(setq *layers-S*
  (list
    (list "S-ALGN" 2 "CENTER2" "Alignment")
    (list "S-BEAM" 7 "Continuous" "Beams")
    (list "S-BEAM-ALUM" 7 "Continuous" "Beams: aluminum")
    (list "S-BEAM-CONC" 7 "Continuous" "Beams: concrete")
    (list "S-BEAM-STEL" 7 "Continuous" "Beams: steel")
    (list "S-BEAM-WOOD" 7 "Continuous" "Beams: wood")
    (list "S-BRCG" 7 "Continuous" "Bracing")
    (list "S-BRCG-ALUM" 7 "Continuous" "Bracing: aluminum")
    (list "S-BRCG-ALUM-HORZ" 7 "Continuous" "Bracing: aluminum: horizontal")
    (list "S-BRCG-ALUM-VERT" 7 "Continuous" "Bracing: aluminum: vertical")
    (list "S-BRCG-METL" 7 "Continuous" "Bracing: metal")
    (list "S-BRCG-STEL" 7 "Continuous" "Bracing: steel")
    (list "S-BRCG-STEL-HORZ" 7 "Continuous" "Bracing: steel: horizontal")
    (list "S-BRCG-STEL-VERT" 7 "Continuous" "Bracing: steel: vertical")
    (list "S-BRCG-WOOD" 7 "Continuous" "Bracing: wood")
    (list "S-BRCG-WOOD-HORZ" 7 "Continuous" "Bracing: wood: horizontal")
    (list "S-BRCG-WOOD-VERT" 7 "Continuous" "Bracing: wood: vertical")
    (list "S-COLS" 7 "Continuous" "Columns")
    (list "S-COLS-ABLT" 3 "Continuous" "Columns: anchor bolts")
    (list "S-COLS-ALUM" 7 "Continuous" "Columns: aluminum")
    (list "S-COLS-CONC" 7 "Continuous" "Columns: concrete")
    (list "S-COLS-STEL" 7 "Continuous" "Columns: steel")
    (list "S-COLS-WOOD" 7 "Continuous" "Columns: wood")
    (list "S-DECK" 3 "Continuous" "Deck")
    (list "S-DECK-FLOR" 3 "Continuous" "Deck: floor")
    (list "S-DECK-FLOR-OPNG" 2 "Continuous" "Deck: floor: openings")
    (list "S-DECK-ROOF" 3 "Continuous" "Deck: roof")
    (list "S-DECK-ROOF-OPNG" 2 "Continuous" "Deck: roof: openings")
    (list "S-DETL" 2 "Continuous" "Detail")
    (list "S-DETL-HSSS" 2 "Continuous" "Detail: hollow structural steel")
    (list "S-DETL-PLYW" 2 "Continuous" "Detail: plywood")
    (list "S-DETL-W2XS" 2 "Continuous" "Detail: dimension lumber")
    (list "S-FNDN" 9 "Continuous" "Foundation")
    (list "S-FNDN-FTNG" 9 "Continuous" "Foundation: footings")
    (list "S-FNDN-GRBM" 9 "Continuous" "Foundation: grade beams")
    (list "S-FNDN-PCAP" 9 "Continuous" "Foundation: pile caps")
    (list "S-FNDN-PIER" 9 "Continuous" "Foundation: drilled piers")
    (list "S-FNDN-PILE" 9 "Continuous" "Foundation: piles")
    (list "S-FNDN-RBAR" 3 "Continuous" "Foundation: reinforcing bar")
    (list "S-FNDN-RBAR-BOT1" 3 "Continuous" "Foundation: reinforcing bar: bottom group 1")
    (list "S-FNDN-RBAR-BOT2" 3 "Continuous" "Foundation: reinforcing bar: bottom group 2")
    (list "S-FNDN-RBAR-TOP1" 3 "Continuous" "Foundation: reinforcing bar: top group 1")
    (list "S-FNDN-RBAR-TOP2" 3 "Continuous" "Foundation: reinforcing bar: top group 2")
    (list "S-FRAM" 7 "Continuous" "Braced frame or moment frame")
    (list "S-FSTN" 3 "Continuous" "Fasteners and connections")
    (list "S-GATE" 5 "Continuous" "Gate")
    (list "S-GRID" 1 "CENTER2" "Grids")
    (list "S-GRID-EXTR" 1 "CENTER2" "Grids: exterior")
    (list "S-GRID-INTR" 1 "CENTER2" "Grids: interior")
    (list "S-GRLN" 2 "Continuous" "Grade line")
    (list "S-GRLN-SURF" 2 "Continuous" "Grade line: surface areas")
    (list "S-GRTG" 3 "Continuous" "Grating")
    (list "S-GRTG-OVHD" 3 "HIDDEN2" "Grating: overhead")
    (list "S-HYDR" 9 "Continuous" "Hydraulic structure")
    (list "S-JNTS" 3 "Continuous" "Joints")
    (list "S-JNTS-CNTJ" 3 "Continuous" "Joints: construction joint")
    (list "S-JNTS-CTLJ" 3 "Continuous" "Joints: control joint")
    (list "S-JNTS-EXPJ" 3 "Continuous" "Joints: expansion joint")
    (list "S-JOIS" 3 "Continuous" "Joists")
    (list "S-JOIS-BRGX" 3 "Continuous" "Joists: bridging")
    (list "S-LNTL" 7 "Continuous" "Lintels")
    (list "S-PADS" 9 "Continuous" "Pads")
    (list "S-PADS-EQPM" 9 "Continuous" "Pads: equipment")
    (list "S-PLAT" 7 "Continuous" "Platform")
    (list "S-PLAT-FRMG" 7 "Continuous" "Platform: framing")
    (list "S-PLAT-GRTG" 3 "Continuous" "Platform: grating")
    (list "S-SIGN" 2 "Continuous" "Sign")
    (list "S-SIGN-BOUY" 2 "Continuous" "Sign: bouy")
    (list "S-SIGN-FRMG" 7 "Continuous" "Sign: framing")
    (list "S-SIGN-GAGE" 2 "Continuous" "Sign: gauge (staff)")
    (list "S-SIGN-TEXT" 2 "Continuous" "Sign: signage text")
    (list "S-SIGN-XTRU" 3 "Continuous" "Sign: extrusion")
    (list "S-SLAB" 9 "Continuous" "Slab")
    (list "S-SLAB-CONC" 9 "Continuous" "Slab: concrete")
    (list "S-SLAB-EDGE" 9 "Continuous" "Slab: edge")
    (list "S-SLAB-OPNG" 2 "Continuous" "Slab: openings (and depressions)")
    (list "S-SLAB-OPNX" 1 "Continuous" "Slab: opening indication (x)")
    (list "S-SLAB-STEL" 9 "Continuous" "Slab: steel")
    (list "S-SLAB-WOOD" 9 "Continuous" "Slab: wood")
    (list "S-STIF" 3 "Continuous" "Stiffener")
    (list "S-STIF-LONG" 3 "Continuous" "Stiffener: longitudinal")
    (list "S-STIF-TRAV" 3 "Continuous" "Stiffener: transverse")
    (list "S-STRS" 3 "Continuous" "Stairs")
    (list "S-STRS-LADD" 3 "Continuous" "Stairs: ladders and ladder assemblies")
    (list "S-TRUS" 7 "Continuous" "Trusses")
    (list "S-WALL" 9 "Continuous" "Walls")
    (list "S-WALL-ABOV" 7 "HIDDEN2" "Walls: above")
    (list "S-WALL-CMUW" 9 "Continuous" "Walls: concrete masonry unit")
    (list "S-WALL-CONC" 9 "Continuous" "Walls: concrete")
    (list "S-WALL-MSNW" 9 "Continuous" "Walls: masonry")
    (list "S-WALL-PCST" 9 "Continuous" "Walls: pre-cast concrete")
    (list "S-WALL-SHEA" 9 "Continuous" "Walls: structural bearing or shear walls")
    (list "S-WALL-STEL" 7 "Continuous" "Walls: steel stud")
    (list "S-WALL-VENR" 3 "Continuous" "Walls: veneer")
    (list "S-WALL-WOOD" 7 "Continuous" "Walls: wood")
  )
)

(setq *layers-V*
  (list
    (list "V-BLDG" 14 "Continuous" "Buildings and primary structures")
    (list "V-BLDG-DECK" 14 "Continuous" "Buildings and primary structures: deck")
    (list "V-BLDG-OTLN" 14 "Continuous" "Buildings and primary structures: outline")
    (list "V-BLDG-OVHD" 14 "HIDDEN2" "Buildings and primary structures: overhead")
    (list "V-BLDG-PRCH" 14 "Continuous" "Buildings and primary structures: porch")
    (list "V-BNDY" 6 "Continuous" "Political boundaries")
    (list "V-BNDY-BORO" 6 "Continuous" "Political boundaries: borough")
    (list "V-BNDY-CITY" 6 "Continuous" "Political boundaries: city")
    (list "V-BNDY-CNTY" 6 "Continuous" "Political boundaries: county")
    (list "V-BNDY-CORP" 6 "Continuous" "Political boundaries: corporation")
    (list "V-BNDY-NATL" 6 "Continuous" "Political boundaries: national")
    (list "V-BNDY-PROV" 6 "Continuous" "Political boundaries: province")
    (list "V-BNDY-STAT" 6 "Continuous" "Political boundaries: state")
    (list "V-BNDY-TSHP" 6 "Continuous" "Political boundaries: town or township")
    (list "V-BNDY-ZONE" 6 "Continuous" "Political boundaries: zoning")
    (list "V-BORE" 14 "Continuous" "Borings")
    (list "V-BRDG" 14 "Continuous" "Bridge")
    (list "V-BRDG-BENT" 14 "Continuous" "Bridge: top of bent")
    (list "V-BRDG-CNTR" 14 "CENTER2" "Bridge: center")
    (list "V-BRDG-CTLJ" 14 "Continuous" "Bridge: control joint")
    (list "V-BRDG-DECK" 14 "Continuous" "Bridge: deck")
    (list "V-BRDG-GRAL" 14 "Continuous" "Bridge: guard rail")
    (list "V-BRKL" 14 "Continuous" "Break/fault lines")
    (list "V-BRKL-BOTB" 14 "Continuous" "Break/fault lines: bottom of bank")
    (list "V-BRKL-FLOW" 14 "Continuous" "Break/fault lines: flowline")
    (list "V-BRKL-TOPB" 14 "Continuous" "Break/fault lines: top of bank")
    (list "V-BRLN" 6 "Continuous" "Building restriction line")
    (list "V-BZNA" 2 "Continuous" "Buffer zone area")
    (list "V-CHAN" 14 "Continuous" "Navigable channels")
    (list "V-CHAN-BWTR" 14 "Continuous" "Navigable channels: breakwater")
    (list "V-CHAN-CNTR" 14 "CENTER2" "Navigable channels: center")
    (list "V-CHAN-DACL" 14 "Continuous" "Navigable channels: de-authorized channel limits")
    (list "V-CHAN-DOCK" 14 "Continuous" "Navigable channels: decks, docks, floats, piers")
    (list "V-CHAN-NAID" 2 "Continuous" "Navigable channels: navigation aids")
    (list "V-COMM" 4 "Continuous" "Communications")
    (list "V-COMM-MHOL" 4 "Continuous" "Communications: manhole")
    (list "V-COMM-OVHD" 4 "HIDDEN2" "Communications: overhead")
    (list "V-COMM-POLE" 4 "Continuous" "Communications: pole")
    (list "V-COMM-UGND" 4 "HIDDEN2" "Communications: underground")
    (list "V-CTRL" 14 "Continuous" "Control points")
    (list "V-CTRL-BMRK" 14 "Continuous" "Control points: benchmarks")
    (list "V-CTRL-FLYS" 14 "Continuous" "Control points: fly station")
    (list "V-CTRL-GRID" 14 "CENTER2" "Control points: grid")
    (list "V-CTRL-HORZ" 14 "Continuous" "Control points: horizontal")
    (list "V-CTRL-HVPT" 14 "Continuous" "Control points: horizontal/vertical")
    (list "V-CTRL-PNPT" 14 "Continuous" "Control points: panel points")
    (list "V-CTRL-TRAV" 14 "Continuous" "Control points: transverse")
    (list "V-CTRL-VERT" 14 "Continuous" "Control points: vertical")
    (list "V-DRIV" 12 "Continuous" "Driveways")
    (list "V-DRIV-ASPH" 12 "Continuous" "Driveways: asphalt")
    (list "V-DRIV-CNTR" 14 "CENTER2" "Driveways: center")
    (list "V-DRIV-CONC" 12 "Continuous" "Driveways: concrete")
    (list "V-DRIV-CURB" 13 "Continuous" "Driveways: curb")
    (list "V-DRIV-FLNE" 1 "Continuous" "Driveways: fire lane")
    (list "V-DRIV-GRVL" 12 "Continuous" "Driveways: gravel")
    (list "V-DRIV-MRKG" 2 "Continuous" "Driveways: pavement markings")
    (list "V-DRIV-UPVD" 12 "Continuous" "Driveways: unpaved surface")
    (list "V-DTCH" 13 "Continuous" "Ditches or washes")
    (list "V-DTCH-BOTM" 14 "Continuous" "Ditches or washes: bottom")
    (list "V-DTCH-CNTR" 14 "CENTER2" "Ditches or washes: center")
    (list "V-DTCH-EWAT" 14 "Continuous" "Ditches or washes: edge of water")
    (list "V-DTCH-TOP" 14 "Continuous" "Ditches or washes: top")
    (list "V-ESMT" 2 "DASHED2" "Easements")
    (list "V-ESMT-ACCS" 2 "DASHED2" "Easements: access")
    (list "V-ESMT-CATV" 2 "DASHED2" "Easements: cable television system")
    (list "V-ESMT-CONS" 2 "DASHED2" "Easements: conservation")
    (list "V-ESMT-CSTG" 2 "DASHED2" "Easements: construction/grading")
    (list "V-ESMT-ELEC" 2 "DASHED2" "Easements: electrical")
    (list "V-ESMT-FDPL" 2 "DASHED2" "Easements: flood plain")
    (list "V-ESMT-INEG" 2 "DASHED2" "Easements: ingress/egress")
    (list "V-ESMT-LSCP" 2 "DASHED2" "Easements: landscape")
    (list "V-ESMT-NGAS" 2 "DASHED2" "Easements: natural gas line")
    (list "V-ESMT-PHON" 2 "DASHED2" "Easements: telephone line")
    (list "V-ESMT-ROAD" 2 "DASHED2" "Easements: roadway")
    (list "V-ESMT-ROAD-PERM" 2 "DASHED2" "Easements: roadway: permanent")
    (list "V-ESMT-ROAD-TEMP" 2 "DASHED2" "Easements: roadway: temporary")
    (list "V-ESMT-RWAY" 2 "DASHED2" "Easements: right-of-way")
    (list "V-ESMT-SGHT" 2 "DASHED2" "Easements: sight distance")
    (list "V-ESMT-SSWR" 2 "DASHED2" "Easements: sanitary sewer")
    (list "V-ESMT-STRM" 2 "DASHED2" "Easements: storm sewer")
    (list "V-ESMT-SWMT" 2 "DASHED2" "Easements: storm water management")
    (list "V-ESMT-TRAL" 2 "DASHED2" "Easements: trail or path")
    (list "V-ESMT-UTIL" 2 "DASHED2" "Easements: utility lines")
    (list "V-ESMT-WATR" 2 "DASHED2" "Easements: water supply")
    (list "V-FLHA" 11 "Continuous" "Flood hazard area")
    (list "V-FUEL" 4 "Continuous" "Fuel systems")
    (list "V-FUEL-MHOL" 4 "Continuous" "Fuel systems: manhole")
    (list "V-FUEL-PIPE" 4 "Continuous" "Fuel systems: piping")
    (list "V-FUEL-TANK" 4 "Continuous" "Fuel systems: storage tanks")
    (list "V-FUEL-UGND" 4 "HIDDEN2" "Fuel systems: underground")
    (list "V-NGAS" 4 "Continuous" "Natural gas systems")
    (list "V-NGAS-MHOL" 4 "Continuous" "Natural gas systems: manhole")
    (list "V-NGAS-PIPE" 4 "Continuous" "Natural gas systems: piping")
    (list "V-NGAS-TANK" 4 "Continuous" "Natural gas systems: storage tanks")
    (list "V-NGAS-UGND" 4 "HIDDEN2" "Natural gas systems: underground")
    (list "V-NODE" 14 "Continuous" "Node")
    (list "V-NODE-ABUT" 14 "Continuous" "Node: abutment")
    (list "V-NODE-ACTL" 14 "Continuous" "Node: aerial horizontal and vertical control points")
    (list "V-NODE-BLDG" 14 "Continuous" "Node: building points")
    (list "V-NODE-BLIN" 14 "Continuous" "Node: baseline")
    (list "V-NODE-BRDG" 14 "Continuous" "Node: bridge survey points")
    (list "V-NODE-BRKL" 14 "Continuous" "Node: break lines and spot elevation points")
    (list "V-NODE-BROW" 14 "Continuous" "Node: brush row points")
    (list "V-NODE-BRSH" 14 "Continuous" "Node: brush points")
    (list "V-NODE-CABL" 4 "Continuous" "Node: underground cable systems")
    (list "V-NODE-CURB" 14 "Continuous" "Node: curb")
    (list "V-NODE-DASP" 2 "Continuous" "Node: description attributes for survey points")
    (list "V-NODE-DECK" 14 "Continuous" "Node: deck")
    (list "V-NODE-DRIV" 12 "Continuous" "Node: driveway")
    (list "V-NODE-EASP" 2 "Continuous" "Node: elevation attributes for survey points")
    (list "V-NODE-EXPJ" 14 "Continuous" "Node: expansion joint")
    (list "V-NODE-GRND" 14 "Continuous" "Node: ground")
    (list "V-NODE-MHOL" 14 "Continuous" "Node: manhole")
    (list "V-NODE-MRKG" 2 "Continuous" "Node: pavement markings")
    (list "V-NODE-NGAS" 4 "Continuous" "Node: natural gas line")
    (list "V-NODE-PASP" 2 "Continuous" "Node: point number attributes for survey points")
    (list "V-NODE-PIPE" 4 "Continuous" "Node: piping (driveway/roadway culverts)")
    (list "V-NODE-POLE" 4 "Continuous" "Node: pole (power, telephone, etc.)")
    (list "V-NODE-PVMT" 12 "Continuous" "Node: pavement")
    (list "V-NODE-SIGN" 2 "Continuous" "Node: signage")
    (list "V-NODE-SSWR" 4 "Continuous" "Node: sanitary sewer")
    (list "V-NODE-STRM" 4 "Continuous" "Node: storm sewer")
    (list "V-NODE-SWLK" 12 "Continuous" "Node: sidewalks")
    (list "V-NODE-TREE" 42 "Continuous" "Node: tree")
    (list "V-NODE-TROW" 42 "Continuous" "Node: tree row")
    (list "V-NODE-WATR" 4 "Continuous" "Node: water supply")
    (list "V-POWR" 4 "Continuous" "Power")
    (list "V-POWR-FENC" 4 "Continuous" "Power: fences")
    (list "V-POWR-INST" 4 "Continuous" "Power: instrumentation")
    (list "V-POWR-MHOL" 4 "Continuous" "Power: manhole")
    (list "V-POWR-OVHD" 4 "HIDDEN2" "Power: overhead")
    (list "V-POWR-POLE" 4 "Continuous" "Power: pole")
    (list "V-POWR-STRC" 4 "Continuous" "Power: structures")
    (list "V-POWR-UGND" 4 "HIDDEN2" "Power: underground")
    (list "V-PRKG" 12 "Continuous" "Parking lots")
    (list "V-PRKG-ASPH" 12 "Continuous" "Parking lots: asphalt")
    (list "V-PRKG-CNTR" 14 "CENTER2" "Parking lots: center")
    (list "V-PRKG-CONC" 12 "Continuous" "Parking lots: concrete")
    (list "V-PRKG-CURB" 13 "Continuous" "Parking lots: curb")
    (list "V-PRKG-DRAN" 14 "Continuous" "Parking lots: drainage slope indications")
    (list "V-PRKG-FLNE" 1 "Continuous" "Parking lots: fire lane")
    (list "V-PRKG-GRVL" 12 "Continuous" "Parking lots: gravel")
    (list "V-PRKG-MRKG" 2 "Continuous" "Parking lots: pavement markings")
    (list "V-PRKG-STRP" 2 "Continuous" "Parking lots: striping")
    (list "V-PRKG-UPVD" 12 "Continuous" "Parking lots: unpaved surface")
    (list "V-PROP" 6 "Continuous" "Property")
    (list "V-PROP-LINE" 6 "Continuous" "Property: lines")
    (list "V-PROP-QTRS" 6 "Continuous" "Property: quarter section")
    (list "V-PROP-RSRV" 6 "Continuous" "Property: reservation")
    (list "V-PROP-SBCK" 2 "DASHED2" "Property: setback lines")
    (list "V-PROP-SECT" 6 "Continuous" "Property: section")
    (list "V-PROP-SUBD" 6 "Continuous" "Property: subdivision (interior) lines")
    (list "V-PROP-SXTS" 6 "Continuous" "Property: sixteenth section")
    (list "V-PVMT" 12 "Continuous" "Pavement")
    (list "V-PVMT-ASPH" 12 "Continuous" "Pavement: asphalt")
    (list "V-PVMT-CONC" 12 "Continuous" "Pavement: concrete")
    (list "V-PVMT-GRVL" 12 "Continuous" "Pavement: gravel")
    (list "V-RAIL" 13 "Continuous" "Railroad")
    (list "V-RAIL-CNTR" 14 "CENTER2" "Railroad: center")
    (list "V-RAIL-EQPM" 4 "Continuous" "Railroad: equipment")
    (list "V-RAIL-TRAK" 13 "Continuous" "Railroad: track")
    (list "V-RIVR" 13 "Continuous" "River")
    (list "V-RIVR-BOTM" 14 "Continuous" "River: bottom")
    (list "V-RIVR-CNTR" 14 "CENTER2" "River: center")
    (list "V-RIVR-EDGE" 13 "Continuous" "River: edge")
    (list "V-RIVR-TOPB" 14 "Continuous" "River: top of bank")
    (list "V-ROAD" 13 "Continuous" "Roadways")
    (list "V-ROAD-ASPH" 12 "Continuous" "Roadways: asphalt")
    (list "V-ROAD-CNTR" 14 "CENTER2" "Roadways: center")
    (list "V-ROAD-CONC" 12 "Continuous" "Roadways: concrete")
    (list "V-ROAD-CURB" 13 "Continuous" "Roadways: curb")
    (list "V-ROAD-FLNE" 1 "Continuous" "Roadways: fire lane")
    (list "V-ROAD-GRVL" 12 "Continuous" "Roadways: gravel")
    (list "V-ROAD-MRKG" 2 "Continuous" "Roadways: pavement markings")
    (list "V-ROAD-UPVD" 12 "Continuous" "Roadways: unpaved surface")
    (list "V-RRAP" 12 "Continuous" "Riprap")
    (list "V-RWAY" 6 "Continuous" "Right-of-way")
    (list "V-RWAY-CNTR" 14 "CENTER2" "Right-of-way: center")
    (list "V-RWAY-CTLA" 6 "Continuous" "Right-of-way: controlled access")
    (list "V-RWAY-LINE" 6 "Continuous" "Right-of-way: lines")
    (list "V-RWAY-LMTA" 6 "Continuous" "Right-of-way: limited access")
    (list "V-RWAY-MRKR" 2 "Continuous" "Right-of-way: marker")
    (list "V-RWAY-STAN" 2 "Continuous" "Right-of-way: stationing")
    (list "V-SITE" 14 "Continuous" "Site features")
    (list "V-SITE-EWAT" 14 "Continuous" "Site features: edge of water")
    (list "V-SITE-FENC" 12 "Continuous" "Site features: fences")
    (list "V-SITE-ROCK" 14 "Continuous" "Site features: large rocks and rock outcroppings")
    (list "V-SITE-RTWL" 13 "Continuous" "Site features: retaining wall")
    (list "V-SITE-SIGN" 2 "Continuous" "Site features: signage")
    (list "V-SITE-VEGE" 42 "Continuous" "Site features: trees, shrubs, and other vegetation")
    (list "V-SSWR" 4 "Continuous" "Sanitary sewer")
    (list "V-SSWR-MHOL" 4 "Continuous" "Sanitary sewer: manhole")
    (list "V-SSWR-PIPE" 4 "Continuous" "Sanitary sewer: piping")
    (list "V-SSWR-STRC" 4 "Continuous" "Sanitary sewer: structures")
    (list "V-SSWR-UGND" 4 "HIDDEN2" "Sanitary sewer: underground")
    (list "V-STEM" 4 "Continuous" "Steam system")
    (list "V-STEM-INST" 4 "Continuous" "Steam system: instrumentation")
    (list "V-STEM-MHOL" 4 "Continuous" "Steam system: manhole")
    (list "V-STEM-PIPE" 4 "Continuous" "Steam system: piping")
    (list "V-STEM-STRC" 4 "Continuous" "Steam system: structures")
    (list "V-STEM-UGND" 4 "HIDDEN2" "Steam system: underground")
    (list "V-STRM" 4 "Continuous" "Storm sewer")
    (list "V-STRM-DTCH" 4 "Continuous" "Storm sewer: ditches or washes")
    (list "V-STRM-MHOL" 4 "Continuous" "Storm sewer: manhole")
    (list "V-STRM-PIPE" 4 "Continuous" "Storm sewer: piping")
    (list "V-STRM-POND" 13 "Continuous" "Storm sewer: retention pond")
    (list "V-STRM-STRC" 4 "Continuous" "Storm sewer: structures")
    (list "V-STRM-UGND" 4 "HIDDEN2" "Storm sewer: underground")
    (list "V-SURV" 14 "Continuous" "Survey")
    (list "V-SURV-DATA" 2 "Continuous" "Survey: data")
    (list "V-SWLK" 12 "Continuous" "Sidewalks")
    (list "V-SWLK-ASPH" 12 "Continuous" "Sidewalks: asphalt")
    (list "V-SWLK-CONC" 12 "Continuous" "Sidewalks: concrete")
    (list "V-TOPO" 14 "Continuous" "Topographic feature")
    (list "V-TOPO-EWAT" 14 "Continuous" "Topographic feature: edge of water")
    (list "V-TOPO-GRID" 14 "CENTER2" "Topographic feature: grid")
    (list "V-TOPO-MAJR" 13 "Continuous" "Topographic feature: major (contours)")
    (list "V-TOPO-MINR" 14 "Continuous" "Topographic feature: minor (contours)")
    (list "V-TOPO-SOUN" 14 "Continuous" "Topographic feature: soundings")
    (list "V-TOPO-SPOT" 2 "Continuous" "Topographic feature: spot elevations")
    (list "V-UNID" 2 "Continuous" "Unidentified site objects")
    (list "V-UNID-CABL" 4 "Continuous" "Unidentified site objects: cable systems")
    (list "V-UNID-PIPE" 4 "Continuous" "Unidentified site objects: piping")
    (list "V-UNID-TANK" 4 "Continuous" "Unidentified site objects: storage tanks")
    (list "V-UNID-UTIL" 4 "Continuous" "Unidentified site objects: utility lines")
    (list "V-UNID-UTIL-OVHD" 4 "HIDDEN2" "Unidentified site objects: utility lines: overhead")
    (list "V-UNID-UTIL-UGND" 4 "HIDDEN2" "Unidentified site objects: utility lines: underground")
    (list "V-WATR" 4 "Continuous" "Water supply")
    (list "V-WATR-INST" 4 "Continuous" "Water supply: instrumentation")
    (list "V-WATR-MHOL" 4 "Continuous" "Water supply: manhole")
    (list "V-WATR-PIPE" 4 "Continuous" "Water supply: piping")
    (list "V-WATR-STRC" 4 "Continuous" "Water supply: structures")
    (list "V-WATR-UGND" 4 "HIDDEN2" "Water supply: underground")
  )
)

(setq *layers-T*
  (list
    (list "T-ALRM" 61 "Continuous" "Alarm system")
    (list "T-BCST" 61 "Continuous" "Broadcast-related system (radio or TV)")
    (list "T-BELL" 61 "Continuous" "Bell system")
    (list "T-CABL" 61 "Continuous" "Cable systems")
    (list "T-CABL-COAX" 61 "Continuous" "Cable systems: coax cable")
    (list "T-CABL-FIBR" 61 "Continuous" "Cable systems: fiber optics cable")
    (list "T-CABL-MULT" 61 "Continuous" "Cable systems: multi-conductor cable")
    (list "T-CABL-TRAY" 61 "Continuous" "Cable systems: cable tray and wireways")
    (list "T-CATV" 61 "Continuous" "Cable television system")
    (list "T-CCTV" 61 "Continuous" "Closed-circuit television system")
    (list "T-CLOK" 61 "Continuous" "Clock system")
    (list "T-CLOK-CIRC" 62 "Continuous" "Clock system: circuits")
    (list "T-CLOK-CLNG" 30 "Continuous" "Clock system: ceiling")
    (list "T-CLOK-CNMB" 2 "Continuous" "Clock system: circuit number")
    (list "T-CLOK-EQPM" 61 "Continuous" "Clock system: equipment")
    (list "T-CLOK-FLOR" 2 "Continuous" "Clock system: floor")
    (list "T-CLOK-WALL" 61 "Continuous" "Clock system: wall")
    (list "T-COMM" 61 "Continuous" "Communications")
    (list "T-COMM-CIRC" 62 "Continuous" "Communications: circuits")
    (list "T-COMM-CLNG" 30 "Continuous" "Communications: ceiling")
    (list "T-COMM-CNMB" 2 "Continuous" "Communications: circuit number")
    (list "T-COMM-EQPM" 61 "Continuous" "Communications: equipment")
    (list "T-COMM-FLOR" 2 "Continuous" "Communications: floor")
    (list "T-COMM-WALL" 61 "Continuous" "Communications: wall")
    (list "T-CONT" 61 "Continuous" "Controls and instrumentation")
    (list "T-CONT-DEVC" 61 "Continuous" "Controls and instrumentation: devices")
    (list "T-CONT-WIRE" 62 "Continuous" "Controls and instrumentation: wiring")
    (list "T-DATA" 61 "Continuous" "Data/LAN system")
    (list "T-DATA-CIRC" 62 "Continuous" "Data/LAN system: circuits")
    (list "T-DATA-CLNG" 30 "Continuous" "Data/LAN system: ceiling")
    (list "T-DATA-CNMB" 2 "Continuous" "Data/LAN system: circuit number")
    (list "T-DATA-EQPM" 61 "Continuous" "Data/LAN system: equipment")
    (list "T-DATA-FLOR" 2 "Continuous" "Data/LAN system: floor")
    (list "T-DATA-JACK" 61 "Continuous" "Data/LAN system: jacks")
    (list "T-DATA-WALL" 61 "Continuous" "Data/LAN system: wall")
    (list "T-DIAG" 2 "Continuous" "Diagrams")
    (list "T-DIAG-ENCL" 2 "Continuous" "Diagrams: equipment enclosures")
    (list "T-DIAG-EQPM" 2 "Continuous" "Diagrams: equipment")
    (list "T-DIAG-GRND" 2 "Continuous" "Diagrams: ground")
    (list "T-DICT" 61 "Continuous" "Dictation system")
    (list "T-DICT-CIRC" 62 "Continuous" "Dictation system: circuits")
    (list "T-DICT-CLNG" 30 "Continuous" "Dictation system: ceiling")
    (list "T-DICT-CNMB" 2 "Continuous" "Dictation system: circuit number")
    (list "T-DICT-EQPM" 61 "Continuous" "Dictation system: equipment")
    (list "T-DICT-FLOR" 2 "Continuous" "Dictation system: floor")
    (list "T-DICT-WALL" 61 "Continuous" "Dictation system: wall")
    (list "T-ELEC" 5 "Continuous" "Electrical system, telecom plan")
    (list "T-EMCS" 61 "Continuous" "Energy monitoring control system")
    (list "T-FIRE" 1 "Continuous" "Fire protection")
    (list "T-FIRE-CIRC" 1 "Continuous" "Fire protection: circuits")
    (list "T-FIRE-CLNG" 30 "Continuous" "Fire protection: ceiling")
    (list "T-FIRE-CNMB" 1 "Continuous" "Fire protection: circuit number")
    (list "T-FIRE-EQPM" 1 "Continuous" "Fire protection: equipment")
    (list "T-FIRE-FLOR" 1 "Continuous" "Fire protection: floor")
    (list "T-FIRE-WALL" 1 "Continuous" "Fire protection: wall")
    (list "T-INTC" 61 "Continuous" "Intercom/PA systems")
    (list "T-NURS" 61 "Continuous" "Nurse call system")
    (list "T-NURS-CIRC" 62 "Continuous" "Nurse call system: circuits")
    (list "T-NURS-CLNG" 30 "Continuous" "Nurse call system: ceiling")
    (list "T-NURS-CNMB" 2 "Continuous" "Nurse call system: circuit number")
    (list "T-NURS-EQPM" 61 "Continuous" "Nurse call system: equipment")
    (list "T-NURS-FLOR" 2 "Continuous" "Nurse call system: floor")
    (list "T-NURS-WALL" 61 "Continuous" "Nurse call system: wall")
    (list "T-PGNG" 61 "Continuous" "Paging system")
    (list "T-PHON" 61 "Continuous" "Telephone system")
    (list "T-PHON-JACK" 61 "Continuous" "Telephone system: jacks")
    (list "T-PROJ" 61 "Continuous" "Projector system")
    (list "T-SERT" 61 "Continuous" "Security system")
    (list "T-SERT-CIRC" 62 "Continuous" "Security system: circuits")
    (list "T-SERT-CLNG" 30 "Continuous" "Security system: ceiling")
    (list "T-SERT-CNMB" 2 "Continuous" "Security system: circuit number")
    (list "T-SERT-EQPM" 61 "Continuous" "Security system: equipment")
    (list "T-SERT-FLOR" 2 "Continuous" "Security system: floor")
    (list "T-SERT-WALL" 61 "Continuous" "Security system: wall")
    (list "T-SOUN" 61 "Continuous" "Sound system")
    (list "T-TRAN" 61 "Continuous" "Transmission system (RF and microwave)")
    (list "T-TVAN" 61 "Continuous" "Television antenna system")
    (list "T-TVAN-CIRC" 62 "Continuous" "Television antenna system: circuits")
    (list "T-TVAN-CLNG" 30 "Continuous" "Television antenna system: ceiling")
    (list "T-TVAN-CNMB" 2 "Continuous" "Television antenna system: circuit number")
    (list "T-TVAN-EQPM" 61 "Continuous" "Television antenna system: equipment")
    (list "T-TVAN-FLOR" 2 "Continuous" "Television antenna system: floor")
    (list "T-TVAN-WALL" 61 "Continuous" "Television antenna system: wall")
    (list "T-TVVS" 61 "Continuous" "Television and video systems")
    (list "T-TVVS-SAUD" 61 "Continuous" "Television and video systems: audio signal")
    (list "T-TVVS-SCOM" 61 "Continuous" "Television and video systems: communications signal")
    (list "T-TVVS-SCTL" 61 "Continuous" "Television and video systems: control signal")
    (list "T-TVVS-SDAT" 61 "Continuous" "Television and video systems: data signal")
    (list "T-TVVS-SDGA" 61 "Continuous" "Television and video systems: digital audio signal")
    (list "T-TVVS-SDGV" 61 "Continuous" "Television and video systems: digital video signal")
    (list "T-TVVS-SMIC" 61 "Continuous" "Television and video systems: microphone signal")
    (list "T-TVVS-SPWR" 62 "Continuous" "Television and video systems: power signal")
    (list "T-TVVS-SRFI" 61 "Continuous" "Television and video systems: RF signal")
    (list "T-TVVS-SRGB" 61 "Continuous" "Television and video systems: RGB and component video signal")
    (list "T-TVVS-SSYN" 61 "Continuous" "Television and video systems: sync signal")
    (list "T-TVVS-SVID" 61 "Continuous" "Television and video systems: video signal")
  )
)

(setq *layers-X*
  (list
    (list "X-RIGG" 4 "Continuous" "Other discipline: entertainment rigging/automation systems")
    (list "X-SPFX" 4 "Continuous" "Other discipline: entertainment special effects system")
    (list "X-VIDO" 4 "Continuous" "Other discipline: entertainment projection systems")
  )
)

(setq *aia-discipline-map*
  (list
    (list "A" '*layers-A* "ARCHITECTURAL")
    (list "C" '*layers-C* "CIVIL")
    (list "E" '*layers-E* "ELECTRICAL")
    (list "Q" '*layers-Q* "EQUIPMENT")
    (list "F" '*layers-F* "FIRE PROTECTION")
    (list "G" '*layers-G* "GENERAL")
    (list "B" '*layers-B* "GEOTECHNICAL")
    (list "H" '*layers-H* "HAZARDOUS MATERIALS")
    (list "I" '*layers-I* "INTERIORS")
    (list "L" '*layers-L* "LANDSCAPE")
    (list "M" '*layers-M* "MECHANICAL")
    (list "P" '*layers-P* "PLUMBING")
    (list "R" '*layers-R* "RESOURCE")
    (list "S" '*layers-S* "STRUCTURAL")
    (list "V" '*layers-V* "SURVEY/MAPPING")
    (list "T" '*layers-T* "TELECOMMUNICATIONS")
    (list "X" '*layers-X* "OTHER DISCIPLINES")
  )
)

;;------------------------------------------------------------
;; PART 4: Logic functions
;;------------------------------------------------------------

(defun aia-parse-codes (input / norm codes entry)
  ;; Returns list of discipline-map entries matching input string.
  ;; Handles individual codes (A, M, P) and combos (MEP, AMEP).
  (setq norm  (strcase input)
        codes nil)
  (foreach entry *aia-discipline-map*
    (if (wcmatch norm (strcat "*" (car entry) "*"))
      (setq codes (append codes (list entry)))
    )
  )
  codes
)

(defun create-layers-for-codes (entries)
  (foreach entry entries
    (princ (strcat "\n\n[" (car entry) "] " (caddr entry) "..."))
    (foreach row (eval (cadr entry))
      (apply 'make-layer row)
    )
  )
)

(defun delete-layers-for-codes (entries)
  (foreach entry entries
    (princ (strcat "\n\n[" (car entry) "] " (caddr entry) "..."))
    (foreach row (eval (cadr entry))
      (apply 'delete-layer row)
    )
  )
)

;;------------------------------------------------------------
;; PART 5: Commands
;;------------------------------------------------------------

(defun c:LayAIAcreateAll ( / *error* lay-count del-count del-skip)
  (defun *error* (msg)
    (if (not (member msg '("Function cancelled" "quit / exit abort")))
      (princ (strcat "\nError: " msg)))
    (princ))
  (aia-header "CREATE")
  (create-layers-for-codes *aia-discipline-map*)
  (aia-footer "CREATE")
)

(defun c:LayAIAcreateOnly ( / *error* lay-count del-count del-skip input codes)
  (defun *error* (msg)
    (if (not (member msg '("Function cancelled" "quit / exit abort")))
      (princ (strcat "\nError: " msg)))
    (princ))
  (setq input (getstring "\nEnter discipline codes (e.g. MEP, AMEP, A, EP...): "))
  (setq codes (aia-parse-codes input))
  (aia-header "CREATE")
  (if codes
    (create-layers-for-codes codes)
    (progn
      (princ (strcat "\n  WARNING: No valid discipline codes found in \"" input "\""))
      (princ "\n  Valid codes: A B C E F G H I L M P Q R S T V X")
      (princ "\n  Named combos: MEP  AMEP")
    )
  )
  (aia-footer "CREATE")
)

(defun c:LayAIAdeleteAll ( / *error* lay-count del-count del-skip)
  (defun *error* (msg)
    (if (not (member msg '("Function cancelled" "quit / exit abort")))
      (princ (strcat "\nError: " msg)))
    (princ))
  (aia-header "DELETE")
  (delete-layers-for-codes *aia-discipline-map*)
  (aia-footer "DELETE")
)

(defun c:LayAIAdeleteOnly ( / *error* lay-count del-count del-skip input codes)
  (defun *error* (msg)
    (if (not (member msg '("Function cancelled" "quit / exit abort")))
      (princ (strcat "\nError: " msg)))
    (princ))
  (setq input (getstring "\nEnter discipline codes to delete (e.g. MEP, A, EP...): "))
  (setq codes (aia-parse-codes input))
  (aia-header "DELETE")
  (if codes
    (delete-layers-for-codes codes)
    (progn
      (princ (strcat "\n  WARNING: No valid discipline codes found in \"" input "\""))
      (princ "\n  Valid codes: A B C E F G H I L M P Q R S T V X")
      (princ "\n  Named combos: MEP  AMEP")
    )
  )
  (aia-footer "DELETE")
)
